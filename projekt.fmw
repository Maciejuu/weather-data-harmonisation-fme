FME workspace projekt.fmw

Parameters:
- SourceDataset_CSV2 = $(FME_MF_DIR)metadane_IUNG.csv   # Źródło metadanych stacji IUNG
- prgDataset = $(FME_MF_DIR)PRG.zip   # Źródło danych PRG
- folder = C:\Users\kubam\OneDrive\Pulpit\Dane Meteo   # Wybierz folder zapisu wszystkich danych
- coordSyst = EPSG:2180   # Wskaż układ współrzędnych danych
- separatedWriterIMGW = Tak   # Zapisać surowe dane z IMGW?
- separatedWriterIMGWrain = Tak   # Zapisać surowe dane ze stacji opadowych IMGW?
- separatedWriterEDWIN = Tak   # Zapisać surowe dane z eDWIN?
- separatedWriterIUNG = Tak   # Zapisać surowe dane z IUNG?
- separatedWriterALL = Tak   # Zapisać zagregowane dane z wszystkich źródeł?
- IMGWfilestype = CSV Shapefile   # Wybierz format zapisu danych
- raportTemperature = Tak   # Wykonać raport temperatur z ostatnich pomiarów?
- raportWindMax = Tak   # Wykonać raport porywów wiatru z ostatnich pomiarów?
- raportRain = Tak   # Wykonać raport opadów z ostatnich pomiarów?
- top_n_records = 15   # Ile stacji ująć w raporcie?
- newMetadata = Nie   # Dodać wysokości z NMT do poszczególnych stacji pomiarowych?
- newMetadata2 = Tak   # Dodać dane z PRG do poszczególnych stacji pomiarowych?
- mapTemperature = Tak   # Wygenerować mapę aktualnego rozkładu temperatury?
- mapWind = Tak   # Wygenerować mapę aktualnych porywów wiatru?
- mapRain = Tak   # Wygenerować mapę opadów deszczu z ostatniej godziny?

Readers:
- CSV2_1: CSV2 from $(SourceDataset_CSV2) in EPSG:4326
- SHAPEFILE_1: SHAPEFILE from $(prgDataset)

PythonCreator_2
    PYTHONSOURCE_NEW:
      import fme
      from fme import BaseTransformer
      import fmeobjects


      class FeatureCreator(BaseTransformer):
          """Template Class Interface:
          When using this class, make sure its name is set as the value of the 'Class to Process Features'
          transformer parameter.

          This class inherits from 'fme.BaseTransformer'. For full details of this class, its methods, and
          expected usage, see https://docs.safe.com/fme/html/fmepython/api/fme.html#fme.BaseTransformer.
          """

          def __init__(self):
              """Base constructor for class members."""
              pass

          def input(self, feature: fmeobjects.FMEFeature):
              """This method is called once by FME to initiate feature creation.
              Any number of features can be created and emitted by the self.pyoutput() method.
              The initial feature argument is a placeholder and can be ignored.
              """
              newFeature = fmeobjects.FMEFeature()
              self.pyoutput(newFeature)

          def close(self):
              """This method is called at the end of the class."""
              pass
    PYTHONSYMBOL = FeatureCreator
    -> PythonCaller_4
    -> PythonCaller_3

Bookmark: Inicjalizacja Pythona
PythonCreator
    PYTHONSOURCE_NEW:
      import fme
      from fme import BaseTransformer
      import fmeobjects


      class FeatureCreator(BaseTransformer):
          """Template Class Interface:
          When using this class, make sure its name is set as the value of the 'Class to Process Features'
          transformer parameter.

          This class inherits from 'fme.BaseTransformer'. For full details of this class, its methods, and
          expected usage, see https://docs.safe.com/fme/html/fmepython/api/fme.html#fme.BaseTransformer.
          """

          def __init__(self):
              """Base constructor for class members."""
              pass

          def input(self, feature: fmeobjects.FMEFeature):
              """This method is called once by FME to initiate feature creation.
              Any number of features can be created and emitted by the self.pyoutput() method.
              The initial feature argument is a placeholder and can be ignored.
              """
              newFeature = fmeobjects.FMEFeature()
              self.pyoutput(newFeature)

          def close(self):
              """This method is called at the end of the class."""
              pass
    PYTHONSYMBOL = FeatureCreator
    -> PythonCaller_6
    -> PythonCaller_2
    -> PythonCaller_7
    -> PythonCaller_8

Bookmark: Zapytanie do API IMGW (georeferencja stacji)
PythonCaller_7
    NEW_ATTRIBUTES = kod_stacji uint32 nazwa_stacji char(200) lon real32 lat real32
    PYTHONSOURCE:
      import fme
      import fmeobjects
      import requests

      class FeatureProcessor(object):
          def __init__(self):
              pass

          def input(self, feature):
              pass

          def close(self):
              url = 'https://danepubliczne.imgw.pl/api/data/meteo/format/json'

              try:
                  # Pobranie danych z API IMGW
                  response = requests.get(url, timeout=10)
                  response.raise_for_status()
                  data = response.json()

                  for station in data:
                      # Tworzenie nowego obiektu FME
                      new_feature = fmeobjects.FMEFeature()

                      # Pobieranie i przypisywanie atrybutów
                      kod = station.get('kod_stacji')
                      nazwa = station.get('nazwa_stacji')
                      raw_lon = station.get('lon')
                      raw_lat = station.get('lat')

                      new_feature.setAttribute('kod_stacji', kod)
                      new_feature.setAttribute('nazwa_stacji', nazwa)

                      # Parsowanie współrzędnych i tworzenie geometrii
                      try:
                          if raw_lon and raw_lat:
                              lon = float(raw_lon)
                              lat = float(raw_lat)

                              # Tworzenie punktu (X, Y)
                              point = fmeobjects.FMEPoint(lon, lat)
                              new_feature.setGeometry(point)

                              # Ustawienie układu współrzędnych (WGS84)
                              new_feature.setCoordSys('EPSG:4326')

                              # Zachowanie wartości numerycznych w atrybutach
                              new_feature.setAttribute('lon', lon)
                              new_feature.setAttribute('lat', lat)

                      except ValueError:
                          # Logowanie błędu konwersji dla konkretnej stacji
                          fmeobjects.FMELogFile().logMessageString(
                              f"Błędne współrzędne dla stacji {nazwa} (kod: {kod})",
                              fmeobjects.FME_WARN
                          )

                      # 4. Wypchnięcie obiektu do dalszej części workspace'u
                      self.pyoutput(new_feature)

              except requests.exceptions.RequestException as e:
                  fmeobjects.FMELogFile().logMessageString(
                      f"Błąd połączenia z API IMGW: {str(e)}",
                      fmeobjects.FME_ERROR
                  )
              except Exception as e:
                  fmeobjects.FMELogFile().logMessageString(
                      f"Nieoczekiwany błąd: {str(e)}",
                      fmeobjects.FME_ERROR
                  )
    PYTHONSYMBOL = FeatureProcessor
    -> AttributeManager_6

Bookmark: Zmiana nazw atrybutów
AttributeManager_6
    ATTR_TABLE:
      RENAME_SET_VALUE kod_stacji > statId (uint32)
      RENAME_SET_VALUE nazwa_stacji > StationName (char(200))
      RENAME_SET_VALUE lon > lng (real32)
    -> FeatureJoiner [LEFT]
    -> FeatureJoiner_3 [LEFT]

Bookmark: Pobranie metadanych stacji ze strony zewnętrznej
PythonCaller_8
    NEW_ATTRIBUTES = StationName char(200) lat real64 lng real64
    PYTHONSOURCE:
      import fme
      import fmeobjects
      from selenium import webdriver
      from selenium.webdriver.common.by import By
      from selenium.webdriver.support.ui import Select, WebDriverWait
      from selenium.webdriver.support import expected_conditions as EC

      class FeatureCreator(object):
          def __init__(self):
              # Inicjalizacja loggera FME
              self.logger = fmeobjects.FMELogFile()

          def input(self, feature):
              url = "https://rafalraczynski.com.pl/dane-imgw-mapa/"

              # JS Extract
              js_extract = r"""
              if (typeof mapMarkersArray === 'undefined' <pipe><pipe> !Array.isArray(mapMarkersArray)) return [];
              return mapMarkersArray
                  .filter(l => l.options?.icon?.options?.className?.includes('my-custom-pin'))
                  .map(l => {
                      const tooltip = l.getTooltip()?.getContent() <pipe><pipe> '';
                      const nameMatch = tooltip.match(/<b>(.*?)<\/b>/i);
                      let name = nameMatch ? nameMatch[1] : tooltip.replace(/<[^>]+>/g, '');
                      return {
                          StationName: name.replace(/\[.*?\]/g, '').trim(),
                          lat: l.getLatLng().lat,
                          lng: l.getLatLng().lng
                      };
                  });
              """

              options = webdriver.ChromeOptions()
              options.add_argument("--headless")
              options.add_argument("--no-sandbox")
              options.add_argument("--disable-dev-shm-usage")

              driver = None
              try:
                  driver = webdriver.Chrome(options=options)
                  driver.get(url)
                  wait = WebDriverWait(driver, 30)

                  # Iframe
                  wait.until(EC.frame_to_be_available_and_switch_to_it((By.ID, "meteoFrame")))

                  # Formularz
                  Select(wait.until(EC.element_to_be_clickable((By.ID, "tableSelectUseModel")))).select_by_value("0")
                  driver.find_element(By.ID, "showData").click()

                  # Czekanie na dane w JS
                  wait.until(lambda d: d.execute_script("return (typeof mapMarkersArray !== 'undefined' && mapMarkersArray.length > 0)"))

                  # Pobranie danych
                  raw_data = driver.execute_script(js_extract)

                  # Konwersja na obiekty FME
                  for item in raw_data:
                      new_feature = fmeobjects.FMEFeature()

                      new_feature.setAttribute("StationName", str(item['StationName']))
                      new_feature.setAttribute("lat", float(item['lat']))
                      new_feature.setAttribute("lng", float(item['lng']))

                      # Geometria (X=lng, Y=lat)
                      new_feature.setGeometry(fmeobjects.FMEPoint(item['lng'], item['lat']))
                      new_feature.setCoordSys("LL-WGS84")

                      self.pyoutput(new_feature)

                  # Poprawione logowanie
                  self.logger.logMessageString(f"Selenium: Sukces! Pobrano {len(raw_data)} obiektów.", fmeobjects.FME_INFORM)

              except Exception as e:
                  # Poprawione logowanie błędu
                  self.logger.logMessageString(f"Selenium Error: {str(e)}", fmeobjects.FME_ERROR)

              finally:
                  if driver:
                      driver.quit()

          def close(self):
              pass
    PYTHONSYMBOL = FeatureCreator
    -> FeatureJoiner_5 [RIGHT]

Bookmark: Pobranie danych meteorologicznych ze stacji IMGW
PythonCaller_2
    NEW_ATTRIBUTES = statId int64 temp real32 tempMax24h real32 tempMin24h real32 tempMin12h real32 tempMax12h real32 wilgBezw real32 predWiatru real32 predWiatruMax10min real32 predWiatruMax24h real32 kierWiatru char(200) opad10m real32 opad1h real32 opad1hLastTime real32 opad3h real32 opad6h real32 opad12h real32 opad24h real32 opad24RR real32 opad24RRLastTime real32 tempLastTime datetime statName char(200) opadSum real32 isModel char(200) Typ char(200)
    PYTHONSOURCE:
      import fme
      import fmeobjects
      import pandas as pd
      import requests
      import numpy as np

      class WeatherFetcher(object):
          def __init__(self):
              self.logger = fmeobjects.FMELogFile()

          def input(self, feature):
              url = 'https://rafalraczynski.com.pl/imgw/dane-imgw/getJSON.php?type=table&province=0&order=asc'

              try:
                  # Pobranie danych
                  response = requests.get(url, timeout=20)
                  response.raise_for_status()

                  df = pd.DataFrame(response.json())

                  if df.empty:
                      self.logger.logMessageString("API zwróciło pusty wynik.", fmeobjects.FME_WARN)
                      return

                  # Przetwarzanie (Numpy where)
                  df['Typ'] = np.where(df.get("isModel", False), "Opad", "nieOpad")

                  # Czyszczenie kolumn
                  cols_to_drop = ['provinceId', 'dataPomiaru', 'provName', 'strTime', 'Id']
                  df.drop(columns=[c for c in cols_to_drop if c in df.columns], inplace=True)

                  # Konwersja na obiekty FME
                  for _, row in df.iterrows():
                      new_feature = fmeobjects.FMEFeature()

                      # Iteracja po wszystkich kolumnach
                      for col_name, val in row.items():
                          # Zabezpieczenie przed błędem setAttributeNull
                          if pd.notna(val):
                              # Konwersja na string jest najbezpieczniejsza dla FME
                              new_feature.setAttribute(str(col_name), str(val))
                          else:
                              # ZAMIAST setAttributeNull
                              new_feature.setAttribute(str(col_name), None)

                      self.pyoutput(new_feature)

                  self.logger.logMessageString(f"API Weather: Pobrano {len(df)} rekordów.", fmeobjects.FME_INFORM)

              except Exception as e:
                  self.logger.logMessageString(f"API Error: {str(e)}", fmeobjects.FME_ERROR)

          def close(self):
              pass
    PYTHONSYMBOL = WeatherFetcher
    -> AttributeTrimmer

Bookmark: Poprawa zapisu danych
AttributeTrimmer
    SRC_ATTRS = statName
    TRIM_TO_NONE = Yes
    TRIM_TYPE = BOTH
    -> Tester_7

Bookmark: Odfiltrowanie stacji pogodowych od opadowych
Tester_7
    BOOL_OP = OR
    TEST_CLAUSE = CASE_INSENSITIVE_TEST @Value(isModel) CONTAINS False
    TEST_MODE = CASE_INSENSITIVE_TEST
    PASSED -> FeatureJoiner [RIGHT]
    FAILED -> FeatureJoiner_3 [RIGHT]

Bookmark: Utworzenie zestawu danych przestrzennych
FeatureJoiner
    ATTR_CONFLICT_RES_LOOKUP = USE_RIGHT
    GEOMETRY_HANDLING_LOOKUP = USE_LEFT
    JOIN_KEYS = statId statId NUM
    JOIN_MODE = Inner
    ATTR_CONFLICT_RES = Prefer Right
    GEOMETRY_HANDLING = Prefer Left
    JOINED -> DateTimeConverter
    UNJOINED_RIGHT -> FeatureJoiner_5 [LEFT]
FeatureJoiner_5
    ATTR_CONFLICT_RES_LOOKUP = USE_LEFT
    GEOMETRY_HANDLING_LOOKUP = USE_RIGHT
    JOIN_KEYS = statName StationName AUTO
    JOIN_MODE = Inner
    ATTR_CONFLICT_RES = Prefer Left
    GEOMETRY_HANDLING = Prefer Right
    JOINED -> DateTimeConverter
FeatureJoiner_3
    ATTR_CONFLICT_RES_LOOKUP = USE_RIGHT
    GEOMETRY_HANDLING_LOOKUP = USE_LEFT
    JOIN_KEYS = statId statId NUM
    JOIN_MODE = Inner
    ATTR_CONFLICT_RES = Prefer Right
    GEOMETRY_HANDLING = Prefer Left
    JOINED -> DateTimeConverter_9
    UNJOINED_RIGHT -> FeatureJoiner_4 [RIGHT]
FeatureJoiner_4
    ATTR_CONFLICT_RES_LOOKUP = USE_RIGHT
    GEOMETRY_HANDLING_LOOKUP = USE_LEFT
    JOIN_KEYS = StationName statName AUTO
    JOIN_MODE = Inner
    ATTR_CONFLICT_RES = Prefer Right
    GEOMETRY_HANDLING = Prefer Left
    JOINED -> DuplicateFilter

Bookmark: Harmonizacja czasu (UTC) i odfiltrowanie najnowszych pomiarów ze stacji
DateTimeConverter
    DATETIME_ATTR = tempLastTime
    IN_FORMAT = %Y-%m-%d %H:%M$
    OUT_FORMAT = FME
    PASSTHROUGH = YES
    REPAIR_INPUT = YES
    -> DateTimeStamper
DateTimeStamper
    DATETIME_ATTR = _timenow
    INCLUDE_FRAC_SECONDS = YES
    INCLUDE_OFFSET = NO
    SCOPE = feature
    STAMP_TYPE = datetime
    TIMEZONE = utc
    -> DateTimeCalculator_2
DateTimeCalculator_2
    DAYS = 0
    HOURS = 1
    MINUTES = 10
    MODE = DATETIMECALC_1_ADD_INTERVAL
    MONTHS = 0
    OPERATION_PARAMETERS = START_DATETIME_DATETIMECALC_1_ADD_INTERVAL]@Value(_timenow)]OPERATOR]SUBTRACT]YEARS]0]MONTHS]0]DAYS]0]HOURS]1]MINUTES]10]SECONDS]0]RESULT_DATETIME]_result_datetime]START_DATETIME]@Value(_timenow)
    OPERATOR = SUBTRACT
    RESULT_DATETIME = _result_datetime
    SECONDS = 0
    START_DATETIME = @Value(_timenow)
    START_DATETIME_DATETIMECALC_1_ADD_INTERVAL = @Value(_timenow)
    YEARS = 0
    -> Tester
Tester
    BOOL_OP = OR
    TEST_CLAUSE = CASE_INSENSITIVE_TEST @Value(tempLastTime) >= @Value(_result_datetime)
    TEST_MODE = CASE_INSENSITIVE_TEST
    PASSED -> DateTimeConverter_2
DateTimeConverter_2
    DATETIME_ATTR = tempLastTime
    IN_FORMAT = FME
    OUT_FORMAT = %Y-%m-%d %H:%M
    PASSTHROUGH = YES
    REPAIR_INPUT = YES
    -> Reprojector

Bookmark: Reprojekcja i zmiana układu współrzędnych
Reprojector
    DEST = $(coordSyst)
    INTERPOLATION_TYPE = NearestNeighbor
    RASTER_CELL_SIZE = PreserveCells
    RASTER_TOLERANCE = 0.0
    REPROJECTED -> CoordinateExtractor
CoordinateExtractor
    IND = 0
    RECURSIVE = No
    X_ATTR = x
    Y_ATTR = y
    MODE = Specify Coordinate
    -> CoordinateSystemSetter_3
CoordinateSystemSetter_3
    COORDSYS = $(coordSyst)
    -> AttributeManager

Bookmark: Dostosowanie finalnych tabel, filtracja atrybutów, odrzucanie wartości odstających, sortowanie
AttributeManager
    ATTR_TABLE:
      RENAME_SET_VALUE statId > id (uint32)
      RENAME_SET_VALUE StationName > name (char(200))
      SET_TO ownerId (char(200)) = IMGW
      RENAME_SET_VALUE lat (real32) = @Value(x)
      RENAME_SET_VALUE lng (real32) = @Value(y)
      SET_TO temp (real32) = FME_CONDITIONAL:DEFAULT_VALUE'@Value(temp)'BOOL_OP;OR;COMPOSITE_TEST;1 OR 2;TEST @Value(temp) < -40;TEST @Value(temp) > 45'FME_NULL_VALUE'FME_NUM_CONDITIONS2___
      SET_TO tempMax24h (real32) = FME_CONDITIONAL:DEFAULT_VALUE'@Value(tempMax24h)'BOOL_OP;OR;COMPOSITE_TEST;1 OR 2;TEST @Value(tempMax24h) < -40;TEST @Value(tempMax24h) > 45'FME_NULL_VALUE'FME_NUM_CONDITIONS2___
      SET_TO tempMax12h (real32) = FME_CONDITIONAL:DEFAULT_VALUE'@Value(tempMax12h)'BOOL_OP;OR;COMPOSITE_TEST;1 OR 2;TEST @Value(tempMax12h) < -40;TEST @Value(tempMax12h) > 45'FME_NULL_VALUE'FME_NUM_CONDITIONS2___
      SET_TO tempMin24h (real32) = FME_CONDITIONAL:DEFAULT_VALUE'@Value(tempMin24h)'BOOL_OP;OR;COMPOSITE_TEST;1 OR 2;TEST @Value(tempMin24h) < -40;TEST @Value(tempMin24h) > 45'FME_NULL_VALUE'FME_NUM_CONDITIONS2___
      SET_TO tempMin12h (real32) = FME_CONDITIONAL:DEFAULT_VALUE'@Value(tempMin12h)'BOOL_OP;OR;COMPOSITE_TEST;1 OR 2;TEST @Value(tempMin12h) < -40;TEST @Value(tempMin12h) > 45'FME_NULL_VALUE'FME_NUM_CONDITIONS2___
      RENAME_SET_VALUE opad1h > rain1h (real32) = FME_CONDITIONAL:DEFAULT_VALUE'@Value(rain1h)'BOOL_OP;OR;COMPOSITE_TEST;1 OR 2;TEST @Value(rain1h) > 100;TEST @Value(rain1h) < 0'FME_NULL_VALUE'FME_NUM_CONDITIONS2___
      RENAME_SET_VALUE wilgBezw > humid (real32) = FME_CONDITIONAL:DEFAULT_VALUE'@Value(humid)'BOOL_OP;OR;COMPOSITE_TEST;1 OR 2;TEST @Value(humid) < 0;TEST @Value(humid) > 100'FME_NULL_VALUE'FME_NUM_CONDITIONS2___
      RENAME_SET_VALUE predWiatru > windSpeed (real32) = @Value(windSpeed)
      RENAME_SET_VALUE predWiatruMax10min > windSpeedMax10min (real32) = @Value(windSpeedMax10min)
      RENAME_SET_VALUE predWiatruMax24h > windSpeedMax24h (real32) = @Value(windSpeedMax24h)
      RENAME_SET_VALUE kierWiatru > windDir (char(200))
      SET_TO windDirD (real32) = FME_CONDITIONAL:DEFAULT_VALUE'FME_NULL_VALUE'BOOL_OP;OR;COMPOSITE_TEST;1;TEST @Value(windDir) IN N'0'BOOL_OP;OR;COMPOSITE_TEST;1;TEST @Value(windDir) IN NNE'22.5'BOOL_OP;OR;COMPOSITE_TEST;1;TEST @Value(windDir) IN NE'45'BOOL_OP;OR;COMPOSITE_TEST;1;TEST @Value(windDir) IN ENE'67.5'BOOL_OP;OR;COMPOSITE_TEST;1;TEST @Value(windDir) IN E'90'BOOL_OP;OR;COMPOSITE_TEST;1;TEST @Value(windDir) IN ESE'112.5'BOOL_OP;OR;COMPOSITE_TEST;1;TEST @Value(windDir) IN SE'135'BOOL_OP;OR;COMPOSITE_TEST;1;TEST @Value(windDir) IN SSE'157.5'BOOL_OP;OR;COMPOSITE_TEST;1;TEST @Value(windDir) IN S'180'BOOL_OP;OR;COMPOSITE_TEST;1;TEST @Value(windDir) IN SSW'202.5'BOOL_OP;OR;COMPOSITE_TEST;1;TEST @Value(windDir) IN SW'225'BOOL_OP;OR;COMPOSITE_TEST;1;TEST @Value(windDir) IN WSW'247.5'BOOL_OP;OR;COMPOSITE_TEST;1;TEST @Value(windDir) IN W'270'BOOL_OP;OR;COMPOSITE_TEST;1;TEST @Value(windDir) IN WNW'292.5'BOOL_OP;OR;COMPOSITE_TEST;1;TEST @Value(windDir) IN NW'315'BOOL_OP;OR;COMPOSITE_TEST;1;TEST @Value(windDir) IN NNW'337.5'FME_NUM_CONDITIONS17___
      RENAME_SET_VALUE opad10m > rain10min (real32)
      RENAME_SET_VALUE opad3h > rain3h (real32)
      RENAME_SET_VALUE opad6h > rain6h (real32)
      RENAME_SET_VALUE opad12h > rain12h (real32)
      RENAME_SET_VALUE opad24h > rain24h (real32)
      RENAME_SET_VALUE opad24RR > rain24RR (real32)
      RENAME_SET_VALUE tempLastTime > datetime_utc (buffer)
    USER_EXPOSED_ATTRIBUTES = ownerID,windDir,windDir_2,windDirD,ownerId
    -> AttributeRemover
AttributeRemover
    REMOVE_ATTRS = isModel,statName,Typ,opad1hLastTime,_timenow,opad24RRLastTime,opadSum,_result_datetime,x,y
    -> Tester_8
Tester_8
    BOOL_OP = COMPOSITE
    COMPOSITE_TEST = 1 AND 2
    TEST_CLAUSE:
      TEST @Value(windSpeed) >= 0
      TEST @Value(windSpeed) < 350
    TEST_MODE = TEST
    PASSED -> Sorter_2
Sorter_2
    SORT_PARM = name NATURAL ASCENDING NON_VALUES_AFTER_VALUES
    SORTED -> Sorter_7
    SORTED -> Tester_12
    SORTED -> AttributeKeeper_3

Bookmark: Zapis danych ze stacji meteorologicznych IMGW do formatów wyjściowych
Tester_12
    BOOL_OP = OR
    TEST_CLAUSE = TEST $(separatedWriterIMGW) = Tak
    TEST_MODE = TEST
    PASSED -> Tester_13
    PASSED -> Tester_14
Tester_13
    BOOL_OP = OR
    TEST_CLAUSE = TEST $(IMGWfilestype) != Shapefile
    TEST_MODE = TEST
    PASSED -> FeatureWriter [Sorted]
FeatureWriter
    DATASET = $(folder)
    DATASET_ATTR = _dataset
    FEATURE_TYPE_LIST_ATTR = _feature_types
    FORMAT = SHAPEFILE
    SHAPEFILE_COMPRESSED_FILE = No
    SHAPEFILE_DATASET_SPLITTING = Yes
    SHAPEFILE_DATETIME_STORAGE = TIMESTAMP_STRING
    SHAPEFILE_DESTINATION_DATASETTYPE_VALIDATION = Yes
    SHAPEFILE_DIMENSION = AUTO
    SHAPEFILE_ENCODING = utf-8
    SHAPEFILE_ENFORCE_ATTRIBUTE_LIMIT = No
    SHAPEFILE_MEASURES_AS_Z = No
    SHAPEFILE_PERMIT_NONASCII_FIRST_ATTRNAME = Yes
    SHAPEFILE_REQUIRE_FIRST_ATTRNAME_ALPHA = Yes
    SHAPEFILE_SPATIAL_INDEXES = NONE
    SHAPEFILE_SURFACE_SOLID_STORAGE = PATCH
    TOTAL_FEATURES_WRITTEN_ATTR = _total_features_written
Tester_14
    BOOL_OP = OR
    TEST_CLAUSE = TEST $(IMGWfilestype) != CSV
    TEST_MODE = TEST
    PASSED -> FeatureWriter_2 [Sorted]
FeatureWriter_2
    CSV2_COORDINATE_SYSTEM_GRANULARITY = FEATURE_TYPE
    CSV2_DELIMITER = ,
    CSV2_ENCODING = utf-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = $(folder)
    DATASET_ATTR = _dataset
    FEATURE_TYPE_LIST_ATTR = _feature_types
    FORMAT = CSV2
    TOTAL_FEATURES_WRITTEN_ATTR = _total_features_written

Bookmark: Pobranie metadanych dla stacji opadowych IMGW
PythonCaller_6
    NEW_ATTRIBUTES = StationName char(200) lat real64 lng real64
    PYTHONSOURCE:
      import fme
      import fmeobjects
      from selenium import webdriver
      from selenium.webdriver.common.by import By
      from selenium.webdriver.support.ui import Select, WebDriverWait
      from selenium.webdriver.support import expected_conditions as EC

      class FeatureCreator(object):
          def __init__(self):
              # Inicjalizacja loggera FME
              self.logger = fmeobjects.FMELogFile()

          def input(self, feature):
              url = "https://rafalraczynski.com.pl/dane-imgw-mapa/"

              # JS Extract
              js_extract = r"""
              if (typeof mapMarkersArray === 'undefined' <pipe><pipe> !Array.isArray(mapMarkersArray)) return [];
              return mapMarkersArray
                  .filter(l => l.options?.icon?.options?.className?.includes('my-custom-pin'))
                  .map(l => {
                      const tooltip = l.getTooltip()?.getContent() <pipe><pipe> '';
                      const nameMatch = tooltip.match(/<b>(.*?)<\/b>/i);
                      let name = nameMatch ? nameMatch[1] : tooltip.replace(/<[^>]+>/g, '');
                      return {
                          StationName: name.replace(/\[.*?\]/g, '').trim(),
                          lat: l.getLatLng().lat,
                          lng: l.getLatLng().lng
                      };
                  });
              """

              options = webdriver.ChromeOptions()
              options.add_argument("--headless")
              options.add_argument("--no-sandbox")
              options.add_argument("--disable-dev-shm-usage")

              driver = None
              try:
                  driver = webdriver.Chrome(options=options)
                  driver.get(url)
                  wait = WebDriverWait(driver, 30)

                  # Iframe
                  wait.until(EC.frame_to_be_available_and_switch_to_it((By.ID, "meteoFrame")))

                  # Formularz
                  Select(wait.until(EC.element_to_be_clickable((By.ID, "tableSelectUseModel")))).select_by_value("1")
                  driver.find_element(By.ID, "showData").click()

                  # Czekanie na dane w JS
                  wait.until(lambda d: d.execute_script("return (typeof mapMarkersArray !== 'undefined' && mapMarkersArray.length > 0)"))

                  # Pobranie danych
                  raw_data = driver.execute_script(js_extract)

                  # Konwersja na obiekty FME
                  for item in raw_data:
                      new_feature = fmeobjects.FMEFeature()

                      new_feature.setAttribute("StationName", str(item['StationName']))
                      new_feature.setAttribute("lat", float(item['lat']))
                      new_feature.setAttribute("lng", float(item['lng']))

                      # Geometria (X=lng, Y=lat)
                      new_feature.setGeometry(fmeobjects.FMEPoint(item['lng'], item['lat']))
                      new_feature.setCoordSys("LL-WGS84")

                      self.pyoutput(new_feature)

                  # Poprawione logowanie
                  self.logger.logMessageString(f"Selenium: Sukces! Pobrano {len(raw_data)} obiektów.", fmeobjects.FME_INFORM)

              except Exception as e:
                  # Poprawione logowanie błędu
                  self.logger.logMessageString(f"Selenium Error: {str(e)}", fmeobjects.FME_ERROR)

              finally:
                  if driver:
                      driver.quit()

          def close(self):
              pass
    PYTHONSYMBOL = FeatureCreator
    -> FeatureJoiner_4 [LEFT]

Bookmark: Filtracja duplikatów stacji opadowych
DuplicateFilter
    INPUT_ORDERED_CHOICE_LOOKUP = NO
    KEYATTR = statName
    INPUT_ORDERED_CHOICE = No
    UNIQUE -> DateTimeConverter_9

Bookmark: Harmonizacja czasu (UTC) i odfiltrowanie najnowszych pomiarów ze stacji
DateTimeConverter_9
    DATETIME_ATTR = tempLastTime
    IN_FORMAT = %Y-%m-%d %H:%M$
    OUT_FORMAT = FME
    PASSTHROUGH = YES
    REPAIR_INPUT = YES
    -> DateTimeStamper_4
DateTimeStamper_4
    DATETIME_ATTR = _timenow
    INCLUDE_FRAC_SECONDS = YES
    INCLUDE_OFFSET = NO
    SCOPE = feature
    STAMP_TYPE = datetime
    TIMEZONE = utc
    -> DateTimeCalculator_3
DateTimeCalculator_3
    DAYS = 0
    HOURS = 1
    MINUTES = 10
    MODE = DATETIMECALC_1_ADD_INTERVAL
    MONTHS = 0
    OPERATION_PARAMETERS = START_DATETIME_DATETIMECALC_1_ADD_INTERVAL]@Value(_timenow)]OPERATOR]SUBTRACT]YEARS]0]MONTHS]0]DAYS]0]HOURS]1]MINUTES]10]SECONDS]0]RESULT_DATETIME]_result_datetime]START_DATETIME]@Value(_timenow)
    OPERATOR = SUBTRACT
    RESULT_DATETIME = _result_datetime
    SECONDS = 0
    START_DATETIME = @Value(_timenow)
    START_DATETIME_DATETIMECALC_1_ADD_INTERVAL = @Value(_timenow)
    YEARS = 0
    -> Tester_3
Tester_3
    BOOL_OP = OR
    TEST_CLAUSE = CASE_INSENSITIVE_TEST @Value(tempLastTime) >= @Value(_result_datetime)
    TEST_MODE = CASE_INSENSITIVE_TEST
    PASSED -> DateTimeConverter_7
DateTimeConverter_7
    DATETIME_ATTR = tempLastTime
    IN_FORMAT = FME
    OUT_FORMAT = %Y-%m-%d %H:%M
    PASSTHROUGH = YES
    REPAIR_INPUT = YES
    -> Reprojector_2

Bookmark: Reprojekcja i zmiana układu współrzędnych
Reprojector_2
    DEST = $(coordSyst)
    INTERPOLATION_TYPE = NearestNeighbor
    RASTER_CELL_SIZE = PreserveCells
    RASTER_TOLERANCE = 0.0
    REPROJECTED -> CoordinateExtractor_2
CoordinateExtractor_2
    IND = 0
    RECURSIVE = No
    X_ATTR = x
    Y_ATTR = y
    MODE = Specify Coordinate
    -> CoordinateSystemSetter_4
CoordinateSystemSetter_4
    COORDSYS = $(coordSyst)
    -> AttributeManager_4

Bookmark: Dostosowanie finalnych tabel, filtracja atrybutów, odrzucanie wartości odstających, sortowanie
AttributeManager_4
    ATTR_TABLE:
      RENAME_SET_VALUE statId > id (uint32)
      RENAME_SET_VALUE StationName > name (char(200))
      SET_TO ownerId (char(200)) = IMGW
      SET_TO lat (real32) = @Value(x)
      SET_TO lng (real32) = @Value(y)
      RENAME_SET_VALUE opad24RR > rain24RR (real32)
      RENAME_SET_VALUE tempLastTime > datetime_utc (buffer)
    USER_EXPOSED_ATTRIBUTES = ownerId,windDir,windDirD
    -> AttributeRemover_4
AttributeRemover_4
    REMOVE_ATTRS = isModel,statName,Typ,opad1hLastTime,_timenow,opad24RRLastTime,opadSum,_result_datetime,kierWiatru,opad1h,opad3h,opad6h,opad10m,opad12h,opad24h,predWiatru,predWiatruMax10min,predWiatruMax24h,temp,tempMax12h,tempMax24h,tempMin12h,tempMin24h,wilgBezw,x,y
    -> Sorter_3
Sorter_3
    SORT_PARM = name NATURAL ASCENDING NON_VALUES_AFTER_VALUES
    SORTED -> AttributeKeeper_3

Bookmark: Utworzenie dużej bazy stacji opadowych IMGW i zapis do formatów wyjściowych
AttributeKeeper_3
    CREATE_BULK_MODE_FEATURES = NO
    KEEP_ATTRS = datetime_utc,id,lat,lng,name,ownerId,rain24RR
    -> Sorter_8
Sorter_8
    SORT_PARM = name NATURAL ASCENDING NON_VALUES_AFTER_VALUES
    SORTED -> Tester_24
Tester_24
    BOOL_OP = OR
    TEST_CLAUSE = TEST $(separatedWriterIMGWrain) = Tak
    TEST_MODE = TEST
    PASSED -> Tester_25
    PASSED -> Tester_26
Tester_25
    BOOL_OP = OR
    TEST_CLAUSE = TEST $(IMGWfilestype) != Shapefile
    TEST_MODE = TEST
    PASSED -> FeatureWriter_9 [Sorted]
FeatureWriter_9
    DATASET = $(folder)
    DATASET_ATTR = _dataset
    FEATURE_TYPE_LIST_ATTR = _feature_types
    FORMAT = SHAPEFILE
    SHAPEFILE_COMPRESSED_FILE = No
    SHAPEFILE_DATASET_SPLITTING = Yes
    SHAPEFILE_DATETIME_STORAGE = TIMESTAMP_STRING
    SHAPEFILE_DESTINATION_DATASETTYPE_VALIDATION = Yes
    SHAPEFILE_DIMENSION = AUTO
    SHAPEFILE_ENCODING = utf-8
    SHAPEFILE_ENFORCE_ATTRIBUTE_LIMIT = No
    SHAPEFILE_MEASURES_AS_Z = No
    SHAPEFILE_PERMIT_NONASCII_FIRST_ATTRNAME = Yes
    SHAPEFILE_REQUIRE_FIRST_ATTRNAME_ALPHA = Yes
    SHAPEFILE_SPATIAL_INDEXES = NONE
    SHAPEFILE_SURFACE_SOLID_STORAGE = PATCH
    TOTAL_FEATURES_WRITTEN_ATTR = _total_features_written
Tester_26
    BOOL_OP = OR
    TEST_CLAUSE = TEST $(IMGWfilestype) != CSV
    TEST_MODE = TEST
    PASSED -> FeatureWriter_10 [Sorted]
FeatureWriter_10
    CSV2_COORDINATE_SYSTEM_GRANULARITY = FEATURE_TYPE
    CSV2_DELIMITER = ,
    CSV2_ENCODING = utf-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = $(folder)
    DATASET_ATTR = _dataset
    FEATURE_TYPE_LIST_ATTR = _feature_types
    FORMAT = CSV2
    TOTAL_FEATURES_WRITTEN_ATTR = _total_features_written

Bookmark: Pobranie metadanych stacji eDWIN
PythonCaller_3
    NEW_ATTRIBUTES = id char(200) name char(200) latitude real64 longitude real64 ownerId char(200) stationType char(200)
    PYTHONSOURCE:
      import fme
      import fmeobjects
      import requests

      class EdwinMetaFetcher(object):
          def __init__(self):
              self.logger = fmeobjects.FMELogFile()
              self.TYPES = ['WEATHER', 'RAIN']
              self.API_BASE = 'https://edwin-meteo.apps.paas.psnc.pl'

          def input(self, feature):
              all_stations = []

              # Pobieranie danych
              for t in self.TYPES:
                  try:
                      # Logowanie
                      self.logger.logMessageString(f"Pobieram typ: {t}...", fmeobjects.FME_INFORM)
                      res = requests.get(f'{self.API_BASE}/observationStation?active=true&size=10000&sort=asc&type={t}', timeout=20, verify=False)

                      if res.ok:
                          stations = res.json().get('content', [])
                          all_stations.extend(stations)
                      else:
                          self.logger.logMessageString(f"Błąd HTTP {res.status_code}", fmeobjects.FME_ERROR)
                  except Exception as e:
                      self.logger.logMessageString(f"Wyjątek {t}: {str(e)}", fmeobjects.FME_ERROR)

              if not all_stations:
                  return

              # Tworzenie obiektów FME
              for s in all_stations:
                  new_feature = fmeobjects.FMEFeature()

                  # Przepisanie atrybutów
                  if 'id' in s: new_feature.setAttribute('id', str(s['id']))
                  if 'name' in s: new_feature.setAttribute('name', str(s['name']))
                  if 'ownerId' in s: new_feature.setAttribute('ownerId', str(s['ownerId']))
                  if 'stationType' in s: new_feature.setAttribute('stationType', str(s['stationType']))

                  # Współrzędne bezpośrednio z głównego obiektu
                  lon = s.get('longitude')
                  lat = s.get('latitude')

                  # Tworzenie geometrii
                  if lon is not None and lat is not None:
                      try:
                          # Konwersja na float
                          f_lon = float(lon)
                          f_lat = float(lat)

                          new_feature.setGeometry(fmeobjects.FMEPoint(f_lon, f_lat))
                          new_feature.setCoordSys("LL-WGS84")

                          # Zapis atrybutów
                          new_feature.setAttribute('longitude', f_lon)
                          new_feature.setAttribute('latitude', f_lat)

                          self.pyoutput(new_feature)
                      except ValueError:
                          continue

          def close(self):
              pass
    PYTHONSYMBOL = EdwinMetaFetcher
    -> FeatureJoiner_2 [LEFT]

Bookmark: Pobranie aktualnych danych meteorologicznych ze stacji eDWIN
PythonCaller_4
    NEW_ATTRIBUTES = stationId char(200) measurementDate datetime airTemperature real64 windSpeed real64 windDirection real64 relativeHumidity real64 precipitation real64 airPressure real64 dewPointTemperature real64
    PYTHONSOURCE:
      import fme
      import fmeobjects
      import requests
      import concurrent.futures
      from datetime import datetime, timedelta, timezone

      class EdwinDataFetcher(object):
          def __init__(self):
              self.logger = fmeobjects.FMELogFile()
              self.API_BASE = 'https://edwin-meteo.apps.paas.psnc.pl'
              self.WORKERS = 10
              self.start_date = (datetime.now(timezone.utc) - timedelta(hours=2)).strftime('%Y-%m-%dT%H:%M:%SZ')

          def fetch_station_data(self, session, station_id):
              """Pobiera najnowszy pomiar dla konkretnej stacji"""
              try:

                  url = f'{self.API_BASE}/meteo/station/{station_id}?page=0&size=1&sort=measurementDate,desc&after={self.start_date}'
                  res = session.get(url, timeout=10, verify=False)

                  if res.ok:
                      content = res.json().get('content', [])
                      if content:
                          data = content[0]

                          data.pop('links', None)

                          data['stationId'] = station_id

                          if 'date' in data and 'measurementDate' not in data:
                              data['measurementDate'] = data['date']

                          return data
              except:
                  return None
              return None

          def input(self, feature):
              # Pobranie listy ID stacji
              ids = []
              for t in ['WEATHER', 'RAIN']:
                  try:
                      r = requests.get(f'{self.API_BASE}/observationStation?active=true&size=10000&type={t}', timeout=20, verify=False)
                      if r.ok:
                          ids.extend([x['id'] for x in r.json().get('content', [])])
                  except Exception as e:
                      self.logger.logMessageString(f"Błąd pobierania listy ID ({t}): {e}", fmeobjects.FME_ERROR)

              unique_ids = list(set(ids))

              if not unique_ids:
                  self.logger.logMessageString("Nie znaleziono żadnych aktywnych stacji.", fmeobjects.FME_WARN)
                  return

              self.logger.logMessageString(f"Rozpoczynam pobieranie pomiarów dla {len(unique_ids)} stacji...", fmeobjects.FME_INFORM)

              # Wielowątkowe pobieranie danych
              results = []
              with requests.Session() as session:
                  with concurrent.futures.ThreadPoolExecutor(max_workers=self.WORKERS) as executor:
                      # Mapowanie futures
                      futures = [executor.submit(self.fetch_station_data, session, sid) for sid in unique_ids]

                      for future in concurrent.futures.as_completed(futures):
                          if res := future.result():
                              results.append(res)

              if not results:
                  self.logger.logMessageString("Brak nowych pomiarów w zadanym czasie.", fmeobjects.FME_WARN)
                  return

              # Logowanie struktury pierwszego wyniku
              self.logger.logMessageString(f"DEBUG - STRUKTURA POMIARU: {str(results[0])}", fmeobjects.FME_WARN)

              # 4. Eksport do FME
              for row in results:
                  new_feature = fmeobjects.FMEFeature()

                  for k, v in row.items():
                      if v is not None:
                          new_feature.setAttribute(str(k), str(v))
                      else:
                          new_feature.setAttribute(str(k), None)

                  self.pyoutput(new_feature)

              self.logger.logMessageString(f"Sukces: Pobrano wyniki dla {len(results)} stacji.", fmeobjects.FME_INFORM)

          def close(self):
              pass
    PYTHONSYMBOL = EdwinDataFetcher
    -> FeatureJoiner_2 [RIGHT]

Bookmark: Utworzenie zestawu danych przestrzennych
FeatureJoiner_2
    ATTR_CONFLICT_RES_LOOKUP = USE_RIGHT
    GEOMETRY_HANDLING_LOOKUP = USE_LEFT
    JOIN_KEYS = id stationId AUTO
    JOIN_MODE = Left
    ATTR_CONFLICT_RES = Prefer Right
    GEOMETRY_HANDLING = Prefer Left
    JOINED -> Tester_10
Tester_10
    BOOL_OP = OR
    TEST_CLAUSE = TEST measurementDate ATTRIBUTE_HAS_A_VALUE ""
    TEST_MODE = TEST
    PASSED -> DateTimeConverter_3

Bookmark: Harmonizacja czasu (UTC) i odfiltrowanie najnowszych pomiarów ze stacji eDWIN
DateTimeConverter_3
    DATETIME_ATTR = measurementDate
    IN_FORMAT = %Y-%m-%dT%H:%M:%S%Ez$
    OUT_FORMAT = FME
    PASSTHROUGH = YES
    REPAIR_INPUT = YES
    -> DateTimeStamper_2
DateTimeStamper_2
    DATETIME_ATTR = _timenow
    INCLUDE_FRAC_SECONDS = YES
    INCLUDE_OFFSET = NO
    SCOPE = feature
    STAMP_TYPE = datetime
    TIMEZONE = utc
    -> DateTimeCalculator_4
DateTimeCalculator_4
    DAYS = 0
    HOURS = 1
    MINUTES = 10
    MODE = DATETIMECALC_1_ADD_INTERVAL
    MONTHS = 0
    OPERATION_PARAMETERS = START_DATETIME_DATETIMECALC_1_ADD_INTERVAL]@Value(_timenow)]OPERATOR]SUBTRACT]YEARS]0]MONTHS]0]DAYS]0]HOURS]1]MINUTES]10]SECONDS]0]RESULT_DATETIME]_result_datetime]START_DATETIME]@Value(_timenow)
    OPERATOR = SUBTRACT
    RESULT_DATETIME = _result_datetime
    SECONDS = 0
    START_DATETIME = @Value(_timenow)
    START_DATETIME_DATETIMECALC_1_ADD_INTERVAL = @Value(_timenow)
    YEARS = 0
    -> DateTimeConverter_10
DateTimeConverter_10
    DATETIME_ATTR = measurementDate
    OUT_FORMAT = %Y-%m-%d %H:%M
    PASSTHROUGH = YES
    REPAIR_INPUT = YES
    -> Reprojector_3

Bookmark: Reprojekcja i zmiana układu współrzędnych
Reprojector_3
    DEST = $(coordSyst)
    INTERPOLATION_TYPE = NearestNeighbor
    RASTER_CELL_SIZE = PreserveCells
    RASTER_TOLERANCE = 0.0
    REPROJECTED -> CoordinateExtractor_3
CoordinateExtractor_3
    IND = 0
    RECURSIVE = No
    X_ATTR = x
    Y_ATTR = y
    MODE = Specify Coordinate
    -> CoordinateSystemSetter_5
CoordinateSystemSetter_5
    COORDSYS = $(coordSyst)
    -> Tester_4

Bookmark: Filtracja i odseparowanie stacji meteo od opadowych
Tester_4
    BOOL_OP = OR
    TEST_CLAUSE = CASE_INSENSITIVE_TEST @Value(measurementDate) >= @Value(_result_datetime)
    TEST_MODE = CASE_INSENSITIVE_TEST
    FAILED -> Tester_2
Tester_2
    BOOL_OP = OR
    TEST_CLAUSE = CASE_INSENSITIVE_TEST @Value(stationType) CONTAINS WEATHER
    TEST_MODE = TEST
    PASSED -> AttributeManager_2
    FAILED -> AttributeManager_5

Bookmark: Dostosowanie finalnych tabel, filtracja atrybutów, odrzucanie wartości odstających, sortowanie
AttributeManager_2
    ATTR_TABLE:
      SET_TO ownerId (char(200)) = eDWIN
      RENAME_SET_VALUE latitude > lat (real64) = @Value(x)
      RENAME_SET_VALUE longitude > lng (real64) = @Value(y)
      RENAME_SET_VALUE airTemperature > temp (real64) = FME_CONDITIONAL:DEFAULT_VALUE'@Value(temp)'BOOL_OP;OR;COMPOSITE_TEST;1 OR 2;TEST @Value(temp) < -40;TEST @Value(temp) > 45'FME_NULL_VALUE'FME_NUM_CONDITIONS2___
      RENAME_SET_VALUE windSpeed (real64) = @round(@mult(@Value(windSpeed),3.6),1)
      RENAME_SET_VALUE windDirection > windDirD (real64)
      SET_TO windDir (varchar(200)) = FME_CONDITIONAL:DEFAULT_VALUE'FME_NULL_VALUE'BOOL_OP;OR;COMPOSITE_TEST;1;NUM_TEST @Value(windDirD) RANGE [0,11.25)'N'BOOL_OP;OR;COMPOSITE_TEST;1;NUM_TEST @Value(windDirD) RANGE (11.25,33.75)'NNE'BOOL_OP;OR;COMPOSITE_TEST;1;NUM_TEST @Value(windDirD) RANGE (33.75,56.25)'NE'BOOL_OP;OR;COMPOSITE_TEST;1;NUM_TEST @Value(windDirD) RANGE (56.25,78.75)'ENE'BOOL_OP;OR;COMPOSITE_TEST;1;NUM_TEST @Value(windDirD) RANGE (78.75,101.25)'E'BOOL_OP;OR;COMPOSITE_TEST;1;NUM_TEST @Value(windDirD) RANGE (101.25,123.75)'ESE'BOOL_OP;OR;COMPOSITE_TEST;1;NUM_TEST @Value(windDirD) RANGE (123.75,146.25)'SE'BOOL_OP;OR;COMPOSITE_TEST;1;NUM_TEST @Value(windDirD) RANGE (146.25,168.75)'SSE'BOOL_OP;OR;COMPOSITE_TEST;1;NUM_TEST @Value(windDirD) RANGE (168.75,191.25)'S'BOOL_OP;OR;COMPOSITE_TEST;1;NUM_TEST @Value(windDirD) RANGE (191.25,213.75)'SSW'BOOL_OP;OR;COMPOSITE_TEST;1;NUM_TEST @Value(windDirD) RANGE (213.75,236.25)'SW'BOOL_OP;OR;COMPOSITE_TEST;1;NUM_TEST @Value(windDirD) RANGE (236.25,258.75)'WSW'BOOL_OP;OR;COMPOSITE_TEST;1;NUM_TEST @Value(windDirD) RANGE (258.75,281.25)'W'BOOL_OP;OR;COMPOSITE_TEST;1;NUM_TEST @Value(windDirD) RANGE (281.25,303.75)'WNW'BOOL_OP;OR;COMPOSITE_TEST;1;NUM_TEST @Value(windDirD) RANGE (303.75,326.25)'NW'BOOL_OP;OR;COMPOSITE_TEST;1;NUM_TEST @Value(windDirD) RANGE (326.25,348.75)'NNW'BOOL_OP;OR;COMPOSITE_TEST;1;NUM_TEST @Value(windDirD) RANGE (348.75,360.0]'N'FME_NUM_CONDITIONS18___
      RENAME_SET_VALUE relativeHumidity > humid (real64) = FME_CONDITIONAL:DEFAULT_VALUE'@Value(humid)'BOOL_OP;OR;COMPOSITE_TEST;1 OR 2;TEST @Value(humid) < 0;TEST @Value(humid) > 100'FME_NULL_VALUE'FME_NUM_CONDITIONS2___
      RENAME_SET_VALUE precipitation > rain1h (real64) = FME_CONDITIONAL:DEFAULT_VALUE'@Value(rain1h)'BOOL_OP;OR;COMPOSITE_TEST;1 OR 2;TEST @Value(rain1h) > 0;TEST @Value(rain1h) <= 100'FME_NULL_VALUE'FME_NUM_CONDITIONS2___
      RENAME_SET_VALUE measurementDate > datetime_utc (buffer)
    USER_EXPOSED_ATTRIBUTES = statId,StationName,opad1h,wilgBezw,kierWiatru,predWiatru,tempLastTime,ownerId,windDir
    -> AttributeRemover_2
AttributeRemover_2
    REMOVE_ATTRS = stationId,stationType,_timenow,_result_datetime,x,y
    -> AttributeRounder
AttributeRounder
    PLACES = 1
    ROUND_TYPE_TCL = round
    SRC_ATTRS = humid rain1h temp
    ROUND_TYPE = Nearest
    -> Tester_9
Tester_9
    BOOL_OP = COMPOSITE
    COMPOSITE_TEST = 1 AND 2
    TEST_CLAUSE:
      TEST @Value(windSpeed) >= 0
      TEST @Value(windSpeed) < 350
    TEST_MODE = TEST
    PASSED -> Sorter_4
Sorter_4
    SORT_PARM = name NATURAL ASCENDING NON_VALUES_AFTER_VALUES
    SORTED -> Sorter
    SORTED -> DuplicateFilter_2
    SORTED -> Tester_15

Bookmark: Zapis danych ze stacji meteorologicznych eDWIN do formatów wyjściowych
Tester_15
    BOOL_OP = OR
    TEST_CLAUSE = TEST $(separatedWriterEDWIN) = Tak
    TEST_MODE = TEST
    PASSED -> Tester_16
    PASSED -> Tester_17
Tester_16
    BOOL_OP = OR
    TEST_CLAUSE = TEST $(IMGWfilestype) != Shapefile
    TEST_MODE = TEST
    PASSED -> FeatureWriter_3 [Sorted]
FeatureWriter_3
    DATASET = $(folder)
    DATASET_ATTR = _dataset
    FEATURE_TYPE_LIST_ATTR = _feature_types
    FORMAT = SHAPEFILE
    SHAPEFILE_COMPRESSED_FILE = No
    SHAPEFILE_DATASET_SPLITTING = Yes
    SHAPEFILE_DATETIME_STORAGE = TIMESTAMP_STRING
    SHAPEFILE_DESTINATION_DATASETTYPE_VALIDATION = Yes
    SHAPEFILE_DIMENSION = AUTO
    SHAPEFILE_ENCODING = utf-8
    SHAPEFILE_ENFORCE_ATTRIBUTE_LIMIT = No
    SHAPEFILE_MEASURES_AS_Z = No
    SHAPEFILE_PERMIT_NONASCII_FIRST_ATTRNAME = Yes
    SHAPEFILE_REQUIRE_FIRST_ATTRNAME_ALPHA = Yes
    SHAPEFILE_SPATIAL_INDEXES = NONE
    SHAPEFILE_SURFACE_SOLID_STORAGE = PATCH
    TOTAL_FEATURES_WRITTEN_ATTR = _total_features_written
Tester_17
    BOOL_OP = OR
    TEST_CLAUSE = TEST $(IMGWfilestype) != CSV
    TEST_MODE = TEST
    PASSED -> FeatureWriter_4 [Sorted]
FeatureWriter_4
    CSV2_COORDINATE_SYSTEM_GRANULARITY = FEATURE_TYPE
    CSV2_DELIMITER = ,
    CSV2_ENCODING = utf-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = $(folder)
    DATASET_ATTR = _dataset
    FEATURE_TYPE_LIST_ATTR = _feature_types
    FORMAT = CSV2
    TOTAL_FEATURES_WRITTEN_ATTR = _total_features_written

Bookmark: Zestaw danych ze stacji opadowych eDWIN do dalszego przetwarzania
AttributeManager_5
    ATTR_TABLE:
      SET_TO ownerID (char(200)) = eDWIN
      RENAME_SET_VALUE latitude > lat (real64) = @Value(x)
      RENAME_SET_VALUE longitude > lng (real64) = @Value(y)
      RENAME_SET_VALUE precipitation > rain1h (real64)
      RENAME_SET_VALUE measurementDate > datetime_utc (buffer)
    USER_EXPOSED_ATTRIBUTES = statId,StationName,opad1h,wilgBezw,kierWiatru,predWiatru,tempLastTime,ownerID
    -> AttributeRemover_5
AttributeRemover_5
    REMOVE_ATTRS = stationId,stationType,ownerId,_timenow,airPressure,airTemperature,dewPointTemperature,relativeHumidity,windDirection,windSpeed,_result_datetime,x,y
    -> AttributeRounder_3
AttributeRounder_3
    PLACES = 1
    ROUND_TYPE_TCL = round
    SRC_ATTRS = rain1h
    ROUND_TYPE = Nearest
    -> Sorter_5
Sorter_5
    SORT_PARM = name NATURAL ASCENDING NON_VALUES_AFTER_VALUES

Bookmark: Wczytanie danych IUNG
CSV (reader CSV2_1)
    attributes: id_stacji uint32, station_name varchar(21), Województwo varchar(33), Powiat varchar(29), Gmina/Miasto varchar(33), Y y_coordinate, X x_coordinate
    -> PythonCaller_5

Bookmark: Pobranie danych IUNG i połączenie z metadanymi
PythonCaller_5
    NEW_ATTRIBUTES = data_pomiaru datetime temp real32 temp_5cm real32 temp_g real32 wilg real32 wind_dir int32 wind_gust real32 rain_today real32 rain_yesterday real32
    PYTHONSOURCE:
      import fme
      import fmeobjects
      import requests
      import re
      from concurrent.futures import ThreadPoolExecutor

      class IungFetcher(object):
          def __init__(self):
              self.logger = fmeobjects.FMELogFile()
              self.features = []
              # Wspólna sesja dla wszystkich zapytań
              self.session = requests.Session()
              # Kompilacja regexów
              self.re_data = re.compile(r'data:\s*"([^"]+)"')
              # Maksymalna liczba wątków
              self.max_workers = 5

          def input(self, feature):
              # Oiekty do listy
              self.features.append(feature)

          def fetch_data(self, feature):
              id_stacji = str(feature.getAttribute('id_stacji'))
              url = f"http://meteor.iung.pulawy.pl/data2.php?s={id_stacji}"

              try:
                  response = self.session.get(url, timeout=10)
                  if response.status_code == 200:
                      text = response.text

                      # Parsowanie daty
                      match_data = self.re_data.search(text)
                      if match_data:
                          feature.setAttribute("data_pomiaru", match_data.group(1))

                      # Helpery do wyciągania wartości
                      def get_val(key):
                          m = re.search(rf'{key}:\s*(-?[\d\.]+)', text)
                          return float(m.group(1)) if m else None

                      def get_last_series(key):
                          if key not in text: return None
                          try:
                              fragment = text.split(f'{key}:')[1]
                              if key == 'temperature': fragment = fragment.split('humidity')[0]
                              if key == 'humidity': fragment = fragment.split('yaxis')[0]
                              matches = re.findall(r'\[(\d+),\s*(-?[\d\.]+)\]', fragment)
                              return float(matches[-1][1]) if matches else None
                          except: return None

                      # Mapowanie wartości
                      val_map = {
                          "temp": get_last_series('temperature'),
                          "temp_5cm": get_val("t5Int"),
                          "temp_g": get_val("tg10Int"),
                          "wilg": get_last_series('humidity'),
                          "wind_dir": get_val("windDir"),
                          "wind_gust": get_val("windSpeed"),
                          "rain_today": get_val("rainT"),
                          "rain_yesterday": get_val("rainY")
                      }

                      for k, v in val_map.items():
                          feature.setAttribute(k, float(v) if v is not None else None)
                  else:
                      feature.setAttribute("_error", f"HTTP {response.status_code}")
              except Exception as e:
                  feature.setAttribute("_error", str(e))

              return feature

          def close(self):
              self.logger.logMessageString(f"Rozpoczynanie pobierania dla {len(self.features)} stacji...", fmeobjects.FME_INFORM)

              with ThreadPoolExecutor(max_workers=self.max_workers) as executor:
                  for processed_feature in executor.map(self.fetch_data, self.features):
                      self.pyoutput(processed_feature)

              self.session.close()
    PYTHONSYMBOL = IungFetcher
    -> Tester_6
Tester_6
    BOOL_OP = OR
    TEST_CLAUSE = TEST data_pomiaru ATTRIBUTE_HAS_A_VALUE ""
    TEST_MODE = TEST
    PASSED -> DateTimeConverter_5

Bookmark: Harmonizacja czasu (UTC) i odfiltrowanie najnowszych pomiarów ze stacji IUNG
DateTimeConverter_5
    DATETIME_ATTR = data_pomiaru
    IN_FORMAT = %Y-%m-%d %H:%M$
    OUT_FORMAT = FME
    PASSTHROUGH = YES
    REPAIR_INPUT = YES
    -> DateTimeCalculator
DateTimeCalculator
    DAYS = 0
    HOURS = 1
    MINUTES = 0
    MODE = DATETIMECALC_1_ADD_INTERVAL
    MONTHS = 0
    OPERATION_PARAMETERS = START_DATETIME_DATETIMECALC_1_ADD_INTERVAL]@Value(data_pomiaru)]OPERATOR]SUBTRACT]YEARS]0]MONTHS]0]DAYS]0]HOURS]1]MINUTES]0]SECONDS]0]RESULT_DATETIME]data_pomiaru]START_DATETIME]@Value(data_pomiaru)
    OPERATOR = SUBTRACT
    RESULT_DATETIME = data_pomiaru
    SECONDS = 0
    START_DATETIME = @Value(data_pomiaru)
    START_DATETIME_DATETIMECALC_1_ADD_INTERVAL = @Value(data_pomiaru)
    YEARS = 0
    -> DateTimeStamper_3
DateTimeStamper_3
    DATETIME_ATTR = _timenow
    INCLUDE_FRAC_SECONDS = YES
    INCLUDE_OFFSET = NO
    SCOPE = feature
    STAMP_TYPE = datetime
    TIMEZONE = utc
    -> DateTimeCalculator_5
DateTimeCalculator_5
    DAYS = 0
    HOURS = 1
    MINUTES = 10
    MODE = DATETIMECALC_1_ADD_INTERVAL
    MONTHS = 0
    OPERATION_PARAMETERS = START_DATETIME_DATETIMECALC_1_ADD_INTERVAL]@Value(_timenow)]OPERATOR]SUBTRACT]YEARS]0]MONTHS]0]DAYS]0]HOURS]1]MINUTES]10]SECONDS]0]RESULT_DATETIME]_result_datetime]START_DATETIME]@Value(_timenow)
    OPERATOR = SUBTRACT
    RESULT_DATETIME = _result_datetime
    SECONDS = 0
    START_DATETIME = @Value(_timenow)
    START_DATETIME_DATETIMECALC_1_ADD_INTERVAL = @Value(_timenow)
    YEARS = 0
    -> Reprojector_4

Bookmark: Reprojekcja i zmiana układu współrzędnych
Reprojector_4
    DEST = $(coordSyst)
    INTERPOLATION_TYPE = NearestNeighbor
    RASTER_CELL_SIZE = PreserveCells
    RASTER_TOLERANCE = 0.0
    REPROJECTED -> CoordinateExtractor_4
CoordinateExtractor_4
    IND = 0
    RECURSIVE = No
    X_ATTR = x
    Y_ATTR = y
    MODE = Specify Coordinate
    -> CoordinateSystemSetter_6
CoordinateSystemSetter_6
    COORDSYS = $(coordSyst)
    -> Tester_5

Bookmark: Dostosowanie finalnych tabel, filtracja atrybutów, odrzucanie wartości odstających, sortowanie
Tester_5
    BOOL_OP = OR
    TEST_CLAUSE = CASE_INSENSITIVE_TEST @Value(data_pomiaru) >= @Value(_result_datetime)
    TEST_MODE = CASE_INSENSITIVE_TEST
    PASSED -> AttributeManager_3
AttributeManager_3
    ATTR_TABLE:
      RENAME_SET_VALUE id_stacji > id (uint32)
      RENAME_SET_VALUE station_name > name (varchar(21))
      SET_TO ownerId (char(200)) = IUNG
      RENAME_SET_VALUE Y > lat (real64) = @Value(x)
      RENAME_SET_VALUE X > lng (real64) = @Value(y)
      SET_TO temp (real32) = FME_CONDITIONAL:DEFAULT_VALUE'@Value(temp)'BOOL_OP;OR;COMPOSITE_TEST;1 OR 2;TEST @Value(temp) < -40;TEST @Value(temp) > 45'FME_NULL_VALUE'FME_NUM_CONDITIONS2___
      RENAME_SET_VALUE temp_5cm > temp5cm (real32)
      RENAME_SET_VALUE temp_g > tempGround (real32)
      RENAME_SET_VALUE wilg > humid (real32) = FME_CONDITIONAL:DEFAULT_VALUE'@Value(humid)'BOOL_OP;OR;COMPOSITE_TEST;1 OR 2;TEST @Value(humid) < 0;TEST @Value(humid) > 100'FME_NULL_VALUE'FME_NUM_CONDITIONS2___
      SET_TO windDir (char(200)) = FME_CONDITIONAL:DEFAULT_VALUE'_FME_NO_OP_'BOOL_OP;OR;COMPOSITE_TEST;1;NUM_TEST @Value(wind_dir) RANGE [0,11.25)'N'BOOL_OP;OR;COMPOSITE_TEST;1;NUM_TEST @Value(wind_dir) RANGE (11.25,33.75)'NNE'BOOL_OP;OR;COMPOSITE_TEST;1;NUM_TEST @Value(wind_dir) RANGE (33.75,56.25)'NE'BOOL_OP;OR;COMPOSITE_TEST;1;NUM_TEST @Value(wind_dir) RANGE (56.25,78.75)'ENE'BOOL_OP;OR;COMPOSITE_TEST;1;NUM_TEST @Value(wind_dir) RANGE (78.75,101.25)'E'BOOL_OP;OR;COMPOSITE_TEST;1;NUM_TEST @Value(wind_dir) RANGE (101.25,123.75)'ESE'BOOL_OP;OR;COMPOSITE_TEST;1;NUM_TEST @Value(wind_dir) RANGE (123.75,146.25)'SE'BOOL_OP;OR;COMPOSITE_TEST;1;NUM_TEST @Value(wind_dir) RANGE (146.25,168.75)'SSE'BOOL_OP;OR;COMPOSITE_TEST;1;NUM_TEST @Value(wind_dir) RANGE (168.75,191.25)'S'BOOL_OP;OR;COMPOSITE_TEST;1;NUM_TEST @Value(wind_dir) RANGE (191.25,213.75)'SSW'BOOL_OP;OR;COMPOSITE_TEST;1;NUM_TEST @Value(wind_dir) RANGE (213.75,236.25)'SW'BOOL_OP;OR;COMPOSITE_TEST;1;NUM_TEST @Value(wind_dir) RANGE (236.25,258.75)'WSW'BOOL_OP;OR;COMPOSITE_TEST;1;NUM_TEST @Value(wind_dir) RANGE (258.75,281.25)'W'BOOL_OP;OR;COMPOSITE_TEST;1;NUM_TEST @Value(wind_dir) RANGE (281.25,303.75)'WNW'BOOL_OP;OR;COMPOSITE_TEST;1;NUM_TEST @Value(wind_dir) RANGE (303.75,326.25)'NW'BOOL_OP;OR;COMPOSITE_TEST;1;NUM_TEST @Value(wind_dir) RANGE (326.25,348.75)'NNW'BOOL_OP;OR;COMPOSITE_TEST;1;NUM_TEST @Value(wind_dir) RANGE (348.75,360.0]'N'FME_NUM_CONDITIONS18___
      RENAME_SET_VALUE wind_dir > windDirD (int32)
      RENAME_SET_VALUE wind_gust > windSpeed (real32) = @round(@mult(@Value(windSpeed),3.6),1)
      RENAME_SET_VALUE rain_today > rainToday (real32)
      RENAME_SET_VALUE rain_yesterday > rainYesterday (real32)
      RENAME_SET_VALUE data_pomiaru > datetime_utc (datetime)
    USER_EXPOSED_ATTRIBUTES = ownerId,windDir
    -> DateTimeConverter_6
DateTimeConverter_6
    DATETIME_ATTR = datetime_utc
    IN_FORMAT = FME
    OUT_FORMAT = %Y-%m-%d %H:%M
    PASSTHROUGH = YES
    REPAIR_INPUT = YES
    -> AttributeRemover_3
AttributeRemover_3
    REMOVE_ATTRS = _timenow,Gmina/Miasto,Powiat,Województwo,_result_datetime,x,y
    -> Tester_11
Tester_11
    BOOL_OP = COMPOSITE
    COMPOSITE_TEST = 1 AND 2
    TEST_CLAUSE:
      TEST @Value(windSpeed) >= 0
      TEST @Value(windSpeed) < 350
    TEST_MODE = TEST
    PASSED -> AttributeRounder_2
AttributeRounder_2
    PLACES = 1
    ROUND_TYPE_TCL = round
    SRC_ATTRS = humid temp rainToday rainYesterday temp5cm tempGround windSpeed windDirD
    ROUND_TYPE = Nearest
    -> DuplicateFilter_2
    -> CoordinateSystemSetter_2

Bookmark: Wykrycie duplikatów eDWIN i IUNG
DuplicateFilter_2
    INPUT_ORDERED_CHOICE_LOOKUP = NO
    KEYATTR = name
    INPUT_ORDERED_CHOICE = No
    DUPLICATE -> AttributeKeeper
AttributeKeeper
    CREATE_BULK_MODE_FEATURES = NO
    KEEP_ATTRS = lat,lng,name
    -> AttributeRenamer
AttributeRenamer
    ATTR_TABLE:
      RENAME_SET_DEFAULT lat > lat_edwin
      RENAME_SET_DEFAULT lng > lng_edwin
    KEEP_RENAMED_ONLY = no
    MISSING_INPUT_ATTRS = REMOVE
    -> CoordinateSystemSetter
CoordinateSystemSetter
    COORDSYS = $(coordSyst)
    -> FeatureJoiner_6 [LEFT]

Bookmark: Pozostawienie współrzędnych dla danych IUNG z danych eDWIN
CoordinateSystemSetter_2
    COORDSYS = $(coordSyst)
    -> FeatureJoiner_6 [RIGHT]
FeatureJoiner_6
    ATTR_CONFLICT_RES_LOOKUP = USE_RIGHT
    GEOMETRY_HANDLING_LOOKUP = USE_LEFT
    JOIN_KEYS = name name AUTO
    JOIN_MODE = Inner
    ATTR_CONFLICT_RES = Prefer Right
    GEOMETRY_HANDLING = Prefer Left
    JOINED -> AttributeRemover_6
    UNJOINED_RIGHT -> AttributeManager_7
AttributeRemover_6
    REMOVE_ATTRS = lat,lng
    -> AttributeRenamer_2
AttributeRenamer_2
    ATTR_TABLE:
      RENAME_SET_DEFAULT lat_edwin > lat
      RENAME_SET_DEFAULT lng_edwin > lng
    KEEP_RENAMED_ONLY = no
    MISSING_INPUT_ATTRS = REMOVE
    -> AttributeManager_7
AttributeManager_7
    -> Sorter_6

Bookmark: Finalny zestaw danych IUNG
Sorter_6
    SORT_PARM = name NATURAL ASCENDING NON_VALUES_AFTER_VALUES
    SORTED -> Sorter
    SORTED -> Tester_18

Bookmark: Łączenie danych eDWIN z IUNG
Sorter
    SORT_PARM = name NATURAL ASCENDING NON_VALUES_AFTER_VALUES datetime_utc NATURAL DESCENDING NON_VALUES_AFTER_VALUES
    SORTED -> DuplicateFilter_3
DuplicateFilter_3
    INPUT_ORDERED_CHOICE_LOOKUP = NO
    KEYATTR = name
    INPUT_ORDERED_CHOICE = No
    UNIQUE -> Sorter_7

Bookmark: Agregacja wszystkich źródeł danych w jedno (IMGW, eDWIN, IUNG)
Sorter_7
    SORT_PARM = name NATURAL ASCENDING NON_VALUES_AFTER_VALUES
    SORTED -> AttributeKeeper_2
AttributeKeeper_2
    CREATE_BULK_MODE_FEATURES = NO
    KEEP_ATTRS = datetime_utc,humid,id,lat,lng,name,ownerId,rain1h,temp,windDir,windDirD,windSpeed
    -> StringCaseChanger
StringCaseChanger
    ATTRCHOICE = SELECTED
    ATTRLIST = name
    CHANGE_TYPE = title
    -> Tester_30

Bookmark: Dodanie nowych metadanych
Tester_30
    BOOL_OP = OR
    TEST_CLAUSE = TEST $(newMetadata) = Tak
    TEST_MODE = TEST
    PASSED -> Decelerator
    FAILED -> PointOnAreaOverlayer [POINT]

Bookmark: Zapytanie do API GUGiK o dane z NMT
Decelerator
    DECEL_LOOKUP = PERFEATDELAY
    DELAY = 0.05
    DECEL_TYPE = Per Feature Delay
    -> HTTPCaller
HTTPCaller
    CLIENT_CERTIFICATE_TYPE = NONE
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = altitude
    TARGET_ATTR_ENCODING = auto-detect
    TARGET_URL = https://services.gugik.gov.pl/nmt/?request=GetHByXY&x=@Value(lng)&y=@Value(lat)
    TRANSFER_TIMEOUT_LENGTH = 90
    USE_COOKIES = No
    VERIFY_SSL_CERTIFICATES = Yes
    -> Sorter_12
    <REJECTED> -> Sorter_12
Sorter_12
    SORT_PARM = name NATURAL ASCENDING NON_VALUES_AFTER_VALUES
    SORTED -> Tester_34
Tester_34
    BOOL_OP = OR
    TEST_CLAUSE = TEST $(newMetadata2) = Tak
    TEST_MODE = TEST
    PASSED -> PointOnAreaOverlayer [POINT]
    FAILED -> AttributeManager_8

Bookmark: Zapis danych IUNG do formatów wyjściowych
Tester_18
    BOOL_OP = OR
    TEST_CLAUSE = TEST $(separatedWriterIUNG) = Tak
    TEST_MODE = TEST
    PASSED -> Tester_19
    PASSED -> Tester_20
Tester_19
    BOOL_OP = OR
    TEST_CLAUSE = TEST $(IMGWfilestype) != Shapefile
    TEST_MODE = TEST
    PASSED -> FeatureWriter_5 [Sorted]
FeatureWriter_5
    DATASET = $(folder)
    DATASET_ATTR = _dataset
    FEATURE_TYPE_LIST_ATTR = _feature_types
    FORMAT = SHAPEFILE
    SHAPEFILE_COMPRESSED_FILE = No
    SHAPEFILE_DATASET_SPLITTING = Yes
    SHAPEFILE_DATETIME_STORAGE = TIMESTAMP_STRING
    SHAPEFILE_DESTINATION_DATASETTYPE_VALIDATION = Yes
    SHAPEFILE_DIMENSION = AUTO
    SHAPEFILE_ENCODING = utf-8
    SHAPEFILE_ENFORCE_ATTRIBUTE_LIMIT = No
    SHAPEFILE_MEASURES_AS_Z = No
    SHAPEFILE_PERMIT_NONASCII_FIRST_ATTRNAME = Yes
    SHAPEFILE_REQUIRE_FIRST_ATTRNAME_ALPHA = Yes
    SHAPEFILE_SPATIAL_INDEXES = NONE
    SHAPEFILE_SURFACE_SOLID_STORAGE = PATCH
    TOTAL_FEATURES_WRITTEN_ATTR = _total_features_written
Tester_20
    BOOL_OP = OR
    TEST_CLAUSE = TEST $(IMGWfilestype) != CSV
    TEST_MODE = TEST
    PASSED -> FeatureWriter_6 [Sorted]
FeatureWriter_6
    CSV2_COORDINATE_SYSTEM_GRANULARITY = FEATURE_TYPE
    CSV2_DELIMITER = ,
    CSV2_ENCODING = utf-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = $(folder)
    DATASET_ATTR = _dataset
    FEATURE_TYPE_LIST_ATTR = _feature_types
    FORMAT = CSV2
    TOTAL_FEATURES_WRITTEN_ATTR = _total_features_written

Bookmark: Wczytanie danych z PRG
A01_Granice_wojewodztw (reader SHAPEFILE_1)
    attributes: JPT_KOD_JE varchar(20), JPT_SJR_KO varchar(3), JPT_NAZWA_ varchar(128), JPT_POWIER double, JPT_ORGAN_ varchar(254), JPT_KOD__1 varchar(3), JPT_NAZWA1 varchar(3), JPT_ORGAN1 varchar(3), JPT_WAZNA_ varchar(3), IIP_PRZEST varchar(20), IIP_IDENTY varchar(128), JPT_KJ_IIP varchar(20), JPT_KJ_I_1 varchar(128), JPT_KJ_I_2 varchar(32), JPT_SPS_KO varchar(3), JPT_POWI_1 double, JPT_KJ_I_3 varchar(3), JPT_JOR_ID double, WERSJA_OD varchar(21), WERSJA_DO varchar(21), WAZNY_OD varchar(21), WAZNY_DO varchar(21), IIP_WERSJA varchar(32), JPT_OPIS varchar(254), JPT_ID double, REGON varchar(20), Shape_Leng double, Shape_Area double
    -> AttributeKeeper_4
A02_Granice_powiatow (reader SHAPEFILE_1)
    attributes: JPT_KOD_JE varchar(20), JPT_SJR_KO varchar(3), JPT_NAZWA_ varchar(128), JPT_POWIER double, JPT_ORGAN_ varchar(254), JPT_KOD__1 varchar(3), JPT_NAZWA1 varchar(3), JPT_ORGAN1 varchar(3), JPT_WAZNA_ varchar(3), IIP_PRZEST varchar(20), IIP_IDENTY varchar(128), JPT_KJ_IIP varchar(20), JPT_KJ_I_1 varchar(128), JPT_KJ_I_2 varchar(32), JPT_SPS_KO varchar(3), JPT_POWI_1 double, JPT_KJ_I_3 varchar(3), JPT_JOR_ID double, WERSJA_OD varchar(21), WERSJA_DO varchar(21), WAZNY_OD varchar(21), WAZNY_DO varchar(21), IIP_WERSJA varchar(32), JPT_OPIS varchar(254), JPT_ID double, REGON varchar(20), Shape_Leng double, Shape_Area double
    -> AttributeKeeper_5
A03_Granice_gmin (reader SHAPEFILE_1)
    attributes: JPT_KOD_JE varchar(20), JPT_SJR_KO varchar(3), JPT_NAZWA_ varchar(128), JPT_POWIER double, JPT_ORGAN_ varchar(254), JPT_KOD__1 varchar(3), JPT_NAZWA1 varchar(3), JPT_ORGAN1 varchar(3), JPT_WAZNA_ varchar(3), IIP_PRZEST varchar(20), IIP_IDENTY varchar(128), JPT_KJ_IIP varchar(20), JPT_KJ_I_1 varchar(128), JPT_KJ_I_2 varchar(32), JPT_SPS_KO varchar(3), JPT_POWI_1 double, JPT_KJ_I_3 varchar(3), JPT_JOR_ID double, WERSJA_OD varchar(21), WERSJA_DO varchar(21), WAZNY_OD varchar(21), WAZNY_DO varchar(21), IIP_WERSJA varchar(32), JPT_OPIS varchar(254), JPT_ID double, REGON varchar(20), Shape_Leng double, Shape_Area double
    -> AttributeKeeper_6

Bookmark: Dostosowanie danych PRG do dalszego przetwarzania
AttributeKeeper_4
    CREATE_BULK_MODE_FEATURES = NO
    KEEP_ATTRS = JPT_NAZWA_
    -> Reprojector_5
Reprojector_5
    DEST = $(coordSyst)
    INTERPOLATION_TYPE = NearestNeighbor
    RASTER_CELL_SIZE = PreserveCells
    RASTER_TOLERANCE = 0.0
    REPROJECTED -> PointOnAreaOverlayer [AREA]
    REPROJECTED -> MapnikRasterizer [Województwa]
    REPROJECTED -> MapnikRasterizer_2 [Województwa]
    REPROJECTED -> MapnikRasterizer_3 [Województwa]
AttributeKeeper_5
    CREATE_BULK_MODE_FEATURES = NO
    KEEP_ATTRS = JPT_NAZWA_
    -> Reprojector_6
Reprojector_6
    DEST = $(coordSyst)
    INTERPOLATION_TYPE = NearestNeighbor
    RASTER_CELL_SIZE = PreserveCells
    RASTER_TOLERANCE = 0.0
    REPROJECTED -> PointOnAreaOverlayer_2 [AREA]
    REPROJECTED -> MapnikRasterizer [Powiaty]
    REPROJECTED -> MapnikRasterizer_3 [Powiaty]
    REPROJECTED -> MapnikRasterizer_2 [Powiaty]
AttributeKeeper_6
    CREATE_BULK_MODE_FEATURES = NO
    KEEP_ATTRS = JPT_NAZWA_
    -> Reprojector_7
Reprojector_7
    DEST = $(coordSyst)
    INTERPOLATION_TYPE = NearestNeighbor
    RASTER_CELL_SIZE = PreserveCells
    RASTER_TOLERANCE = 0.0
    REPROJECTED -> PointOnAreaOverlayer_3 [AREA]

Bookmark: Przypisanie danych PRG do stacji meteorologicznych
PointOnAreaOverlayer
    ATTR_ACCUM_MODE = HANDLE_CONFLICT
    ATTR_CONFLICT_RES = ORIGINAL_IF_CONFLICT
    DEAGGREGATE_INPUT = Yes
    OV_ATTR = _woj
    POLYS_FIRST = NO
    POINT -> AttributeRenamer_3
AttributeRenamer_3
    ATTR_TABLE = RENAME_SET_DEFAULT JPT_NAZWA_ > woj
    KEEP_RENAMED_ONLY = no
    MISSING_INPUT_ATTRS = REMOVE
    -> PointOnAreaOverlayer_2 [POINT]
PointOnAreaOverlayer_2
    ATTR_ACCUM_MODE = HANDLE_CONFLICT
    ATTR_CONFLICT_RES = ORIGINAL_IF_CONFLICT
    DEAGGREGATE_INPUT = Yes
    OV_ATTR = _pow
    POLYS_FIRST = NO
    POINT -> AttributeRenamer_4
AttributeRenamer_4
    ATTR_TABLE = RENAME_SET_DEFAULT JPT_NAZWA_ > pow
    KEEP_RENAMED_ONLY = no
    MISSING_INPUT_ATTRS = REMOVE
    -> PointOnAreaOverlayer_3 [POINT]
PointOnAreaOverlayer_3
    ATTR_ACCUM_MODE = HANDLE_CONFLICT
    ATTR_CONFLICT_RES = ORIGINAL_IF_CONFLICT
    DEAGGREGATE_INPUT = Yes
    OV_ATTR = _pow
    POLYS_FIRST = NO
    POINT -> AttributeManager_8

Bookmark: Dostosowanie finalnego zestawu danych
AttributeManager_8
    ATTR_TABLE:
      RENAME_SET_VALUE JPT_NAZWA_ > gmin (varchar(128))
      REMOVE _http_status_code (buffer)
      REMOVE _woj (uint32)
      REMOVE _pow (uint32)
      SET_TO priority (varchar(200)) = FME_CONDITIONAL:DEFAULT_VALUE'_FME_NO_OP_'BOOL_OP;OR;COMPOSITE_TEST;1;TEST @Value(ownerId) = IMGW'1'BOOL_OP;OR;COMPOSITE_TEST;1;TEST @Value(ownerId) = eDWIN'2'BOOL_OP;OR;COMPOSITE_TEST;1;TEST @Value(ownerId) = IUNG'3'FME_NUM_CONDITIONS4___
    USER_EXPOSED_ATTRIBUTES = priority
    -> Tester_21
    -> Tester_29
    -> Tester_28
    -> Tester_27
    -> Tester_31
    -> Tester_32
    -> Tester_33

Bookmark: Tworzenie raportów temperatury
Tester_27
    BOOL_OP = OR
    TEST_CLAUSE = TEST $(raportTemperature) = Tak
    TEST_MODE = TEST
    PASSED -> PythonCaller
PythonCaller
    NEW_ATTRIBUTES = _report varchar(200)
    PYTHONSOURCE:
      import fme
      import fmeobjects

      class ReportGenerator(object):
          def __init__(self):
              self.features = []

          def input(self, feature):
              self.features.append(feature)

          def close(self):
              # 1. Pobranie parametru użytkownika (N rekordów)
              try:
                  limit = int(fme.macroValues.get('top_n_records', 10))
              except (ValueError, TypeError):
                  limit = 50

              # 2. Walidacja i przygotowanie danych
              valid_data = []
              for f in self.features:
                  t_val = f.getAttribute('temp')
                  if t_val is not None and str(t_val).strip() != "":
                      try:
                          # Słownik z potrzebnymi danymi dla wydajności
                          valid_data.append({
                              'name': str(f.getAttribute('name')).title(),
                              'temp': float(t_val),
                              'woj': str(f.getAttribute('woj')),
                              'pow': str(f.getAttribute('pow')),
                              'gmin': str(f.getAttribute('gmin')),
                              'owner': f.getAttribute('ownerId'),
                              'date': f.getAttribute('datetime_utc')
                          })
                      except ValueError:
                          continue

              # 3. Sortowanie dla obu przypadków
              # Najwyższe (descending)
              top_high = sorted(valid_data, key=lambda x: x['temp'], reverse=True)[:limit]
              # Najniższe (ascending)
              top_low = sorted(valid_data, key=lambda x: x['temp'])[:limit]

              # 4. Funkcja pomocnicza do budowania linii raportu
              def build_line(i, data):
                  return f"{i+1}. {data['name']} <pipe> {data['woj']} <pipe> {data['pow']} <pipe> gm. {data['gmin']} <pipe> {data['owner']} <pipe> Temp: {data['temp']}°C <pipe> {data['date']}"

              # 5. Składanie finalnego raportu
              report = []
              report.append(f"=== RAPORT METEO (TOP {limit}) ===")

              report.append("\n[NAJWYŻSZE TEMPERATURY]")
              for i, d in enumerate(top_high):
                  report.append(build_line(i, d))

              report.append("\n[NAJNIŻSZE TEMPERATURY]")
              for i, d in enumerate(top_low):
                  report.append(build_line(i, d))

              report_content = "\n".join(report)

              # 6. Wypchnięcie wyniku do FME
              out_feature = fmeobjects.FMEFeature()
              out_feature.setAttribute('_report', report_content)
              self.pyoutput(out_feature)
    PYTHONSYMBOL = ReportGenerator
    -> AttributeFileWriter
AttributeFileWriter
    CHAR_ENCODING = fme-system
    FILE_NAME = $(folder)/raportTemperatur.txt
    OVERWRITE_FILE_LOOKUP = DestWriteSrcRead
    SOURCE_ATTR = _report
    OVERWRITE_FILE = Overwrite file

Bookmark: Tworzenie raportów prędkości porywów wiatru (tylko dla danych IMGW ze względu na błędy)
Tester_28
    BOOL_OP = OR
    TEST_CLAUSE = TEST $(raportWindMax) = Tak
    TEST_MODE = TEST
    PASSED -> Tester_35
Tester_35
    BOOL_OP = OR
    TEST_CLAUSE = TEST @Value(ownerId) = IMGW
    TEST_MODE = TEST
    PASSED -> PythonCaller_9
PythonCaller_9
    NEW_ATTRIBUTES = _report varchar(200)
    PYTHONSOURCE:
      import fme
      import fmeobjects

      class ReportGenerator(object):
          def __init__(self):
              self.features = []

          def input(self, feature):
              self.features.append(feature)

          def close(self):
              # 1. Pobranie parametru użytkownika (N rekordów)
              try:
                  limit = int(fme.macroValues.get('top_n_records', 10))
              except (ValueError, TypeError):
                  limit = 50

              # 2. Walidacja i przygotowanie danych
              valid_data = []
              for f in self.features:
                  t_val = f.getAttribute('windSpeed')
                  if t_val is not None and str(t_val).strip() != "":
                      try:
                          # Tworzymy słownik z potrzebnymi danymi dla wydajności
                          valid_data.append({
                              'name': str(f.getAttribute('name')).title(),
                              'windSpeed': float(t_val),
                              'woj': str(f.getAttribute('woj')),
                              'pow': str(f.getAttribute('pow')),
                              'gmin': str(f.getAttribute('gmin')),
                              'owner': f.getAttribute('ownerId'),
                              'date': f.getAttribute('datetime_utc')
                          })
                      except ValueError:
                          continue

              # 3. Sortowanie dla obu przypadków
              # Najwyższe (descending)
              top_high = sorted(valid_data, key=lambda x: x['windSpeed'], reverse=True)[:limit]

              # 4. Funkcja pomocnicza do budowania linii raportu
              def build_line(i, data):
                  return f"{i+1}. {data['name']} <pipe> {data['woj']} <pipe> {data['pow']} <pipe> gm. {data['gmin']} <pipe> {data['owner']} <pipe> {data['date']} <pipe> Poryw: {data['windSpeed']} km/h"

              # 5. Składanie finalnego raportu
              report = []
              report.append(f"=== RAPORT METEO (TOP {limit}) ===")

              report.append("\n[NAJWYŻSZE PORYWY WIATRU]")
              for i, d in enumerate(top_high):
                  report.append(build_line(i, d))

              report_content = "\n".join(report)

              # 6. Wypchnięcie wyniku do FME
              out_feature = fmeobjects.FMEFeature()
              out_feature.setAttribute('_report', report_content)
              self.pyoutput(out_feature)
    PYTHONSYMBOL = ReportGenerator
    -> AttributeFileWriter_2
AttributeFileWriter_2
    CHAR_ENCODING = fme-system
    FILE_NAME = $(folder)/raportWiatru.txt
    OVERWRITE_FILE_LOOKUP = DestWriteSrcRead
    SOURCE_ATTR = _report
    OVERWRITE_FILE = Overwrite file

Bookmark: Tworzenie raportów godzinowych opadów
Tester_29
    BOOL_OP = OR
    TEST_CLAUSE = TEST $(raportRain) = Tak
    TEST_MODE = TEST
    PASSED -> PythonCaller_10
PythonCaller_10
    NEW_ATTRIBUTES = _report varchar(200)
    PYTHONSOURCE:
      import fme
      import fmeobjects

      class ReportGenerator(object):
          def __init__(self):
              self.features = []

          def input(self, feature):
              self.features.append(feature)

          def close(self):
              # 1. Pobranie parametru użytkownika (N rekordów)
              try:
                  limit = int(fme.macroValues.get('top_n_records', 10))
              except (ValueError, TypeError):
                  limit = 50

              # 2. Walidacja i przygotowanie danych
              valid_data = []
              for f in self.features:
                  t_val = f.getAttribute('rain1h')
                  if t_val is not None and str(t_val).strip() != "":
                      try:
                          # Tworzymy słownik z potrzebnymi danymi dla wydajności
                          valid_data.append({
                              'name': str(f.getAttribute('name')).title(),
                              'rain1h': float(t_val),
                              'woj': str(f.getAttribute('woj')),
                              'pow': str(f.getAttribute('pow')),
                              'gmin': str(f.getAttribute('gmin')),
                              'owner': f.getAttribute('ownerId'),
                              'date': f.getAttribute('datetime_utc')
                          })
                      except ValueError:
                          continue

              # 3. Sortowanie dla obu przypadków
              # Najwyższe (descending)
              top_high = sorted(valid_data, key=lambda x: x['rain1h'], reverse=True)[:limit]
              # Najniższe (ascending)
              top_low = sorted(valid_data, key=lambda x: x['rain1h'])[:limit]

              # 4. Funkcja pomocnicza do budowania linii raportu
              def build_line(i, data):
                  return f"{i+1}. {data['name']} <pipe> {data['woj']} <pipe> {data['pow']} <pipe> gm. {data['gmin']}  {data['owner']} <pipe> {data['date']} <pipe> Opad: {data['rain1h']} mm"

              # 5. Składanie finalnego raportu
              report = []
              report.append(f"=== RAPORT METEO (TOP {limit}) ===")

              report.append("\n[NAJWYŻSZE OPADY GODZINOWE]")
              for i, d in enumerate(top_high):
                  report.append(build_line(i, d))

              report.append("\n[NAJNIŻSZE OPADY GODZINOWE]")
              for i, d in enumerate(top_low):
                  report.append(build_line(i, d))

              report_content = "\n".join(report)

              # 6. Wypchnięcie wyniku do FME
              out_feature = fmeobjects.FMEFeature()
              out_feature.setAttribute('_report', report_content)
              self.pyoutput(out_feature)
    PYTHONSYMBOL = ReportGenerator
    -> AttributeFileWriter_3
AttributeFileWriter_3
    CHAR_ENCODING = fme-system
    FILE_NAME = $(folder)/raportOpadow.txt
    OVERWRITE_FILE_LOOKUP = DestWriteSrcRead
    SOURCE_ATTR = _report
    OVERWRITE_FILE = Overwrite file

Bookmark: Zapis zagregowanych danych ze wszystkich źródeł do formatów wyjściowych
Tester_21
    BOOL_OP = OR
    TEST_CLAUSE = TEST $(separatedWriterALL) = Tak
    TEST_MODE = TEST
    PASSED -> Tester_22
    PASSED -> Tester_23
Tester_22
    BOOL_OP = OR
    TEST_CLAUSE = TEST $(IMGWfilestype) != Shapefile
    TEST_MODE = TEST
    PASSED -> FeatureWriter_7 [Sorted]
FeatureWriter_7
    DATASET = $(folder)
    DATASET_ATTR = _dataset
    FEATURE_TYPE_LIST_ATTR = _feature_types
    FORMAT = SHAPEFILE
    SHAPEFILE_COMPRESSED_FILE = No
    SHAPEFILE_DATASET_SPLITTING = Yes
    SHAPEFILE_DATETIME_STORAGE = TIMESTAMP_STRING
    SHAPEFILE_DESTINATION_DATASETTYPE_VALIDATION = Yes
    SHAPEFILE_DIMENSION = AUTO
    SHAPEFILE_ENCODING = utf-8
    SHAPEFILE_ENFORCE_ATTRIBUTE_LIMIT = No
    SHAPEFILE_MEASURES_AS_Z = No
    SHAPEFILE_PERMIT_NONASCII_FIRST_ATTRNAME = Yes
    SHAPEFILE_REQUIRE_FIRST_ATTRNAME_ALPHA = Yes
    SHAPEFILE_SPATIAL_INDEXES = NONE
    SHAPEFILE_SURFACE_SOLID_STORAGE = PATCH
    TOTAL_FEATURES_WRITTEN_ATTR = _total_features_written
Tester_23
    BOOL_OP = OR
    TEST_CLAUSE = TEST $(IMGWfilestype) != CSV
    TEST_MODE = TEST
    PASSED -> FeatureWriter_8 [Sorted]
FeatureWriter_8
    CSV2_COORDINATE_SYSTEM_GRANULARITY = FEATURE_TYPE
    CSV2_DELIMITER = ,
    CSV2_ENCODING = utf-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = $(folder)
    DATASET_ATTR = _dataset
    FEATURE_TYPE_LIST_ATTR = _feature_types
    FORMAT = CSV2
    TOTAL_FEATURES_WRITTEN_ATTR = _total_features_written

Bookmark: Utworzenie i zapis rastrowej kompozycji mapowej z aktualnym rozkładem temperatury ze stacji
Tester_31
    BOOL_OP = AND
    TEST_CLAUSE:
      TEST temp ATTRIBUTE_HAS_A_VALUE ""
      TEST $(mapTemperature) = Tak
    TEST_MODE = TEST
    PASSED -> Sorter_9
Sorter_9
    SORT_PARM = priority NUMERIC ASCENDING NON_VALUES_AFTER_VALUES
    SORTED -> MapnikRasterizer [Temperatura]
MapnikRasterizer
    BACKGROUND_COLOR = 1,1,1
    BACKGROUND_COLOR_ALPHA = 1.0
    COLROW_OR_SPACING = RowsColumns
    INTERPRETATION_TYPE = RGBA32
    LAYER_CARDINALITY_LOOKUP = RULES
    MAPNIK_CONFIG = Województwa;line;"__ignore__color-group;FME_DISCLOSURE_OPEN;stroke;0.760784,0.760784,0.760784;stroke-opacity;0.75;__ignore__line-style-group;;stroke-width;1;stroke-linejoin;miter;stroke-linecap;butt;stroke-dasharray;;stroke-miterlimit;4;__ignore__positioning-group;FME_DISCLOSURE_CLOSED;offset;0;__ignore__smoothing-group;FME_DISCLOSURE_CLOSED;stroke-gamma;1;stroke-gamma-method;power;smooth;0;rasterizer;full;__ignore__comp-group;FME_DISCLOSURE_CLOSED;comp-op;src-over;FME_CONTROLLER_QUERY_FILE;;FME_CONTROLLER_CHOICE;line";Powiaty;line;"__ignore__color-group;FME_DISCLOSURE_OPEN;stroke;0.760784,0.760784,0.760784;stroke-opacity;0.5;__ignore__line-style-group;;stroke-width;0.5;stroke-linejoin;miter;stroke-linecap;butt;stroke-dasharray;;stroke-miterlimit;4;__ignore__positioning-group;FME_DISCLOSURE_CLOSED;offset;0;__ignore__smoothing-group;FME_DISCLOSURE_CLOSED;stroke-gamma;1;stroke-gamma-method;power;smooth;0;rasterizer;full;__ignore__comp-group;FME_DISCLOSURE_CLOSED;comp-op;src-over;FME_CONTROLLER_QUERY_FILE;;FME_CONTROLLER_CHOICE;line";Temperatura;text;"__ignore__text-properties-group;FME_DISCLOSURE_OPEN;name;temp;face-name;""FME_CONDITIONAL:DEFAULT_VALUE'Tahoma'BOOL_OP;OR;COMPOSITE_TEST;1;TEST @Value(ownerId) = IMGW'Tahoma,BOLD'FME_NUM_CONDITIONS2___"";size;""FME_CONDITIONAL:BOOL_OP;OR;COMPOSITE_TEST;1;TEST @Value(ownerId) = IMGW'13'BOOL_OP;OR;COMPOSITE_TEST;1;TEST @Value(ownerId) = eDWIN'11'BOOL_OP;OR;COMPOSITE_TEST;1;TEST @Value(ownerId) = IUNG'9'FME_NUM_CONDITIONS4___"";__ignore__color-group;FME_DISCLOSURE_OPEN;fill;""FME_CONDITIONAL:DEFAULT_VALUE'0,0,0'BOOL_OP;AND;COMPOSITE_TEST;1 AND 2;TEST @Value(temp) >= -40;TEST @Value(temp) < -35'1,0,0.784314'BOOL_OP;AND;COMPOSITE_TEST;1 AND 2;TEST @Value(temp) >= -35;TEST @Value(temp) < -30'0.835294,0,1'BOOL_OP;AND;COMPOSITE_TEST;1 AND 2;TEST @Value(temp) >= -30;TEST @Value(temp) < -25'0.611765,0,0.815686'BOOL_OP;AND;COMPOSITE_TEST;1 AND 2;TEST @Value(temp) >= -25;TEST @Value(temp) < -20'0.482353,0,0.780392'BOOL_OP;AND;COMPOSITE_TEST;1 AND 2;TEST @Value(temp) >= -20;TEST @Value(temp) < -15'0.164706,0,0.576471'BOOL_OP;AND;COMPOSITE_TEST;1 AND 2;TEST @Value(temp) >= -15;TEST @Value(temp) < -10'0.00784314,0.247059,0.760784'BOOL_OP;AND;COMPOSITE_TEST;1 AND 2;TEST @Value(temp) >= -10;TEST @Value(temp) < -5'0,0.556863,0.901961'BOOL_OP;AND;COMPOSITE_TEST;1 AND 2;TEST @Value(temp) >= -5;TEST @Value(temp) < -0'0,0.870588,0.917647'BOOL_OP;AND;COMPOSITE_TEST;1 AND 2;TEST @Value(temp) >= -5;TEST @Value(temp) < -0'0,0.870588,0.917647'BOOL_OP;AND;COMPOSITE_TEST;1 AND 2;TEST @Value(temp) >= -0;TEST @Value(temp) < 5'0,0.917647,0.611765'BOOL_OP;AND;COMPOSITE_TEST;1 AND 2;TEST @Value(temp) >= 5;TEST @Value(temp) < 10'0,0.478431,0.184314'BOOL_OP;AND;COMPOSITE_TEST;1 AND 2;TEST @Value(temp) >= 10;TEST @Value(temp) < 15'0.0941176,0.92549,0'BOOL_OP;AND;COMPOSITE_TEST;1 AND 2;TEST @Value(temp) >= 15;TEST @Value(temp) < 20'0.654902,0.890196,0.00392157'BOOL_OP;AND;COMPOSITE_TEST;1 AND 2;TEST @Value(temp) >= 20;TEST @Value(temp) < 25'0.878431,0.92549,0.00392157'BOOL_OP;AND;COMPOSITE_TEST;1 AND 2;TEST @Value(temp) >= 25;TEST @Value(temp) < 30'0.92549,0.662745,0'BOOL_OP;AND;COMPOSITE_TEST;1 AND 2;TEST @Value(temp) >= 30;TEST @Value(temp) < 35'0.92549,0.266667,0.00392157'BOOL_OP;AND;COMPOSITE_TEST;1 AND 2;TEST @Value(temp) >= 35;TEST @Value(temp) < 40'0.807843,0,0'BOOL_OP;AND;COMPOSITE_TEST;1 AND 2;TEST @Value(temp) >= 40;TEST @Value(temp) < 45'0.380392,0.231373,0.231373'FME_NUM_CONDITIONS19___"";opacity;1;halo-fill;1,1,1;halo-radius;0;__ignore__positioning-group;FME_DISCLOSURE_OPEN;text-ratio;0;wrap-width;0;wrap-before;No;spacing;0;character-spacing;0;line-spacing;0;label-position-tolerance;0;dx;0;dy;0;avoid-edges;No;minimum-distance;0;minimum-padding;0;minimum-path-length;0;allow-overlap;No;orientation;0;placement;point;placement-type;dummy;placements;<Unused>;max-char-angle-delta;<Unused>;horizontal-alignment;auto;justify-alignment;auto;vertical-alignment;auto;__ignore__comp-group;FME_DISCLOSURE_OPEN;comp-op;src-over;FME_CONTROLLER_QUERY_FILE;;FME_CONTROLLER_CHOICE;text";Tytuł;text;"__ignore__text-properties-group;FME_DISCLOSURE_OPEN;name;tekst;face-name;Tahoma,BOLD;size;44;__ignore__color-group;FME_DISCLOSURE_OPEN;fill;0,0,0;opacity;1;halo-fill;1,1,1;halo-radius;0;__ignore__positioning-group;FME_DISCLOSURE_OPEN;text-ratio;0;wrap-width;0;wrap-before;No;spacing;0;character-spacing;0;line-spacing;0;label-position-tolerance;0;dx;0;dy;0;avoid-edges;No;minimum-distance;0;minimum-padding;0;minimum-path-length;0;allow-overlap;No;orientation;0;placement;point;placement-type;dummy;placements;<Unused>;max-char-angle-delta;<Unused>;horizontal-alignment;auto;justify-alignment;auto;vertical-alignment;auto;__ignore__comp-group;FME_DISCLOSURE_CLOSED;comp-op;src-over;FME_CONTROLLER_QUERY_FILE;;FME_CONTROLLER_CHOICE;text";Czas;text;"__ignore__text-properties-group;FME_DISCLOSURE_OPEN;name;tekst_czas;face-name;Tahoma,Normal;size;25;__ignore__color-group;FME_DISCLOSURE_OPEN;fill;0,0,0;opacity;1;halo-fill;1,1,1;halo-radius;0;__ignore__positioning-group;FME_DISCLOSURE_CLOSED;text-ratio;0;wrap-width;0;wrap-before;No;spacing;0;character-spacing;0;line-spacing;0;label-position-tolerance;0;dx;0;dy;0;avoid-edges;No;minimum-distance;0;minimum-padding;0;minimum-path-length;0;allow-overlap;No;orientation;0;placement;point;placement-type;dummy;placements;<Unused>;max-char-angle-delta;<Unused>;horizontal-alignment;auto;justify-alignment;auto;vertical-alignment;auto;__ignore__comp-group;FME_DISCLOSURE_CLOSED;comp-op;src-over;FME_CONTROLLER_QUERY_FILE;;FME_CONTROLLER_CHOICE;text"
    NUM_COLUMNS = 1500
    NUM_ROWS = 1500
    SPECIFY_GROUND_EXTENTS = Use input data ground extents
    INTERPRETATION_TYPE_LOOKUP = RGBA32
    LAYER_CARDINALITY = Each rendering rule is a layer
    RASTER -> FeatureWriter_11 [Raster]
FeatureWriter_11
    DATASET = $(folder)
    DATASET_ATTR = _dataset
    FEATURE_TYPE_LIST_ATTR = _feature_types
    FORMAT = PNGRASTER
    PNGRASTER_COORDINATE_SYSTEM_GRANULARITY = FEATURE
    PNGRASTER_FORMAT_ATTRIBUTES_OVERRIDE_FEATURE_TYPE_PARAMETERS = No
    TOTAL_FEATURES_WRITTEN_ATTR = _total_features_written

Bookmark: Utworzenie i zapis rastrowej kompozycji mapowej z aktualnym rozkładem porywów wiatru ze stacji
Tester_32
    BOOL_OP = COMPOSITE
    COMPOSITE_TEST = 1 AND 2
    TEST_CLAUSE:
      TEST windSpeed ATTRIBUTE_HAS_A_VALUE ""
      TEST $(mapWind) = Tak
    TEST_MODE = TEST
    PASSED -> Sorter_10
Sorter_10
    SORT_PARM = priority NUMERIC ASCENDING NON_VALUES_AFTER_VALUES
    SORTED -> MapnikRasterizer_2 [Wiatr]
MapnikRasterizer_2
    BACKGROUND_COLOR = 1,1,1
    BACKGROUND_COLOR_ALPHA = 1.0
    COLROW_OR_SPACING = RowsColumns
    INTERPRETATION_TYPE = RGBA32
    LAYER_CARDINALITY_LOOKUP = RULES
    MAPNIK_CONFIG = Województwa;line;"__ignore__color-group;FME_DISCLOSURE_OPEN;stroke;0.760784,0.760784,0.760784;stroke-opacity;0.75;__ignore__line-style-group;;stroke-width;1;stroke-linejoin;miter;stroke-linecap;butt;stroke-dasharray;;stroke-miterlimit;4;__ignore__positioning-group;FME_DISCLOSURE_CLOSED;offset;0;__ignore__smoothing-group;FME_DISCLOSURE_CLOSED;stroke-gamma;1;stroke-gamma-method;power;smooth;0;rasterizer;full;__ignore__comp-group;FME_DISCLOSURE_CLOSED;comp-op;src-over;FME_CONTROLLER_QUERY_FILE;;FME_CONTROLLER_CHOICE;line";Powiaty;line;"__ignore__color-group;FME_DISCLOSURE_OPEN;stroke;0.760784,0.760784,0.760784;stroke-opacity;0.5;__ignore__line-style-group;;stroke-width;0.5;stroke-linejoin;miter;stroke-linecap;butt;stroke-dasharray;;stroke-miterlimit;4;__ignore__positioning-group;FME_DISCLOSURE_CLOSED;offset;0;__ignore__smoothing-group;FME_DISCLOSURE_CLOSED;stroke-gamma;1;stroke-gamma-method;power;smooth;0;rasterizer;full;__ignore__comp-group;FME_DISCLOSURE_CLOSED;comp-op;src-over;FME_CONTROLLER_QUERY_FILE;;FME_CONTROLLER_CHOICE;line";Wiatr;text;"__ignore__text-properties-group;FME_DISCLOSURE_OPEN;name;windSpeed;face-name;""FME_CONDITIONAL:DEFAULT_VALUE'Tahoma'BOOL_OP;OR;COMPOSITE_TEST;1;TEST @Value(ownerId) = IMGW'Tahoma,BOLD'FME_NUM_CONDITIONS2___"";size;""FME_CONDITIONAL:BOOL_OP;OR;COMPOSITE_TEST;1;TEST @Value(ownerId) = IMGW'13'BOOL_OP;OR;COMPOSITE_TEST;1;TEST @Value(ownerId) = eDWIN'11'BOOL_OP;OR;COMPOSITE_TEST;1;TEST @Value(ownerId) = IUNG'9'FME_NUM_CONDITIONS4___"";__ignore__color-group;FME_DISCLOSURE_OPEN;fill;""FME_CONDITIONAL:DEFAULT_VALUE'0.729412,0,0.666667'BOOL_OP;AND;COMPOSITE_TEST;1 AND 2;TEST @Value(windSpeed) >= 0;TEST @Value(windSpeed) < 15'0,0.831373,1'BOOL_OP;AND;COMPOSITE_TEST;1 AND 2;TEST @Value(windSpeed) >= 15;TEST @Value(windSpeed) < 30'0,0.945098,0.298039'BOOL_OP;AND;COMPOSITE_TEST;1 AND 2;TEST @Value(windSpeed) >= 30;TEST @Value(windSpeed) < 50'0.647059,0.945098,0'BOOL_OP;AND;COMPOSITE_TEST;1 AND 2;TEST @Value(windSpeed) >= 50;TEST @Value(windSpeed) < 75'0.917647,1,0'BOOL_OP;AND;COMPOSITE_TEST;1 AND 2;TEST @Value(windSpeed) >= 75;TEST @Value(windSpeed) < 90'1,0.501961,0'BOOL_OP;AND;COMPOSITE_TEST;1 AND 2;TEST @Value(windSpeed) >= 90;TEST @Value(windSpeed) < 130'1,0,0'FME_NUM_CONDITIONS7___"";opacity;1;halo-fill;1,1,1;halo-radius;0;__ignore__positioning-group;FME_DISCLOSURE_OPEN;text-ratio;0;wrap-width;0;wrap-before;No;spacing;0;character-spacing;0;line-spacing;0;label-position-tolerance;0;dx;0;dy;0;avoid-edges;No;minimum-distance;0;minimum-padding;0;minimum-path-length;0;allow-overlap;No;orientation;0;placement;point;placement-type;dummy;placements;<Unused>;max-char-angle-delta;<Unused>;horizontal-alignment;auto;justify-alignment;auto;vertical-alignment;auto;__ignore__comp-group;FME_DISCLOSURE_OPEN;comp-op;src-over;FME_CONTROLLER_QUERY_FILE;;FME_CONTROLLER_CHOICE;text";Tytuł;text;"__ignore__text-properties-group;FME_DISCLOSURE_OPEN;name;tekst_wiatr;face-name;Tahoma,BOLD;size;44;__ignore__color-group;FME_DISCLOSURE_OPEN;fill;0,0,0;opacity;1;halo-fill;1,1,1;halo-radius;0;__ignore__positioning-group;FME_DISCLOSURE_OPEN;text-ratio;0;wrap-width;0;wrap-before;No;spacing;0;character-spacing;0;line-spacing;0;label-position-tolerance;0;dx;0;dy;0;avoid-edges;No;minimum-distance;0;minimum-padding;0;minimum-path-length;0;allow-overlap;No;orientation;0;placement;point;placement-type;dummy;placements;<Unused>;max-char-angle-delta;<Unused>;horizontal-alignment;auto;justify-alignment;auto;vertical-alignment;auto;__ignore__comp-group;FME_DISCLOSURE_CLOSED;comp-op;src-over;FME_CONTROLLER_QUERY_FILE;;FME_CONTROLLER_CHOICE;text";Czas;text;"__ignore__text-properties-group;FME_DISCLOSURE_OPEN;name;tekst_czas;face-name;Tahoma,Normal;size;25;__ignore__color-group;FME_DISCLOSURE_OPEN;fill;0,0,0;opacity;1;halo-fill;1,1,1;halo-radius;0;__ignore__positioning-group;FME_DISCLOSURE_CLOSED;text-ratio;0;wrap-width;0;wrap-before;No;spacing;0;character-spacing;0;line-spacing;0;label-position-tolerance;0;dx;0;dy;0;avoid-edges;No;minimum-distance;0;minimum-padding;0;minimum-path-length;0;allow-overlap;No;orientation;0;placement;point;placement-type;dummy;placements;<Unused>;max-char-angle-delta;<Unused>;horizontal-alignment;auto;justify-alignment;auto;vertical-alignment;auto;__ignore__comp-group;FME_DISCLOSURE_CLOSED;comp-op;src-over;FME_CONTROLLER_QUERY_FILE;;FME_CONTROLLER_CHOICE;text"
    NUM_COLUMNS = 1500
    NUM_ROWS = 1500
    SPECIFY_GROUND_EXTENTS = Use input data ground extents
    INTERPRETATION_TYPE_LOOKUP = RGBA32
    LAYER_CARDINALITY = Each rendering rule is a layer
    RASTER -> FeatureWriter_12 [Raster]
FeatureWriter_12
    DATASET = $(folder)
    DATASET_ATTR = _dataset
    FEATURE_TYPE_LIST_ATTR = _feature_types
    FORMAT = PNGRASTER
    PNGRASTER_COORDINATE_SYSTEM_GRANULARITY = FEATURE
    PNGRASTER_FORMAT_ATTRIBUTES_OVERRIDE_FEATURE_TYPE_PARAMETERS = No
    TOTAL_FEATURES_WRITTEN_ATTR = _total_features_written

Bookmark: Utworzenie i zapis rastrowej kompozycji mapowej z ostatnimi godzinowymi opadami ze stacji
Tester_33
    BOOL_OP = COMPOSITE
    COMPOSITE_TEST = 1 AND 2
    TEST_CLAUSE:
      TEST rain1h ATTRIBUTE_HAS_A_VALUE ""
      TEST $(mapRain) = Tak
    TEST_MODE = TEST
    PASSED -> Sorter_11
Sorter_11
    SORT_PARM = priority NUMERIC ASCENDING NON_VALUES_AFTER_VALUES
    SORTED -> MapnikRasterizer_3 [Deszcz]
MapnikRasterizer_3
    BACKGROUND_COLOR = 1,1,1
    BACKGROUND_COLOR_ALPHA = 1.0
    COLROW_OR_SPACING = RowsColumns
    INTERPRETATION_TYPE = RGBA32
    LAYER_CARDINALITY_LOOKUP = RULES
    MAPNIK_CONFIG = Województwa;line;"__ignore__color-group;FME_DISCLOSURE_OPEN;stroke;0.760784,0.760784,0.760784;stroke-opacity;0.75;__ignore__line-style-group;;stroke-width;1;stroke-linejoin;miter;stroke-linecap;butt;stroke-dasharray;;stroke-miterlimit;4;__ignore__positioning-group;FME_DISCLOSURE_CLOSED;offset;0;__ignore__smoothing-group;FME_DISCLOSURE_CLOSED;stroke-gamma;1;stroke-gamma-method;power;smooth;0;rasterizer;full;__ignore__comp-group;FME_DISCLOSURE_CLOSED;comp-op;src-over;FME_CONTROLLER_QUERY_FILE;;FME_CONTROLLER_CHOICE;line";Powiaty;line;"__ignore__color-group;FME_DISCLOSURE_OPEN;stroke;0.760784,0.760784,0.760784;stroke-opacity;0.5;__ignore__line-style-group;;stroke-width;0.5;stroke-linejoin;miter;stroke-linecap;butt;stroke-dasharray;;stroke-miterlimit;4;__ignore__positioning-group;FME_DISCLOSURE_CLOSED;offset;0;__ignore__smoothing-group;FME_DISCLOSURE_CLOSED;stroke-gamma;1;stroke-gamma-method;power;smooth;0;rasterizer;full;__ignore__comp-group;FME_DISCLOSURE_CLOSED;comp-op;src-over;FME_CONTROLLER_QUERY_FILE;;FME_CONTROLLER_CHOICE;line";Deszcz;text;"__ignore__text-properties-group;FME_DISCLOSURE_OPEN;name;rain1h;face-name;""FME_CONDITIONAL:DEFAULT_VALUE'Tahoma'BOOL_OP;OR;COMPOSITE_TEST;1;TEST @Value(ownerId) = IMGW'Tahoma,BOLD'FME_NUM_CONDITIONS2___"";size;""FME_CONDITIONAL:BOOL_OP;OR;COMPOSITE_TEST;1;TEST @Value(ownerId) = IMGW'16'BOOL_OP;OR;COMPOSITE_TEST;1;TEST @Value(ownerId) = eDWIN'14'BOOL_OP;OR;COMPOSITE_TEST;1;TEST @Value(ownerId) = IUNG'12'FME_NUM_CONDITIONS4___"";__ignore__color-group;FME_DISCLOSURE_OPEN;fill;""FME_CONDITIONAL:DEFAULT_VALUE'0.862745,0,0.388235'BOOL_OP;OR;COMPOSITE_TEST;1 OR 2;TEST @Value(rain1h) > 0;TEST @Value(rain1h) <= 0.1'0.431373,0.588235,0.737255'BOOL_OP;OR;COMPOSITE_TEST;1 OR 2;TEST @Value(rain1h) > 0.1;TEST @Value(rain1h) <= 0.5'0.45098,0.690196,1'BOOL_OP;OR;COMPOSITE_TEST;1 OR 2;TEST @Value(rain1h) > 0.5;TEST @Value(rain1h) <= 1'0.32549,0.392157,1'BOOL_OP;OR;COMPOSITE_TEST;1 OR 2;TEST @Value(rain1h) > 1;TEST @Value(rain1h) <= 2'0.176471,0.176471,0.8'BOOL_OP;OR;COMPOSITE_TEST;1 OR 2;TEST @Value(rain1h) > 2;TEST @Value(rain1h) <= 5'0.0627451,0,0.541176'BOOL_OP;OR;COMPOSITE_TEST;1 OR 2;TEST @Value(rain1h) > 5;TEST @Value(rain1h) <= 10'0.270588,0.0470588,0.454902'BOOL_OP;OR;COMPOSITE_TEST;1 OR 2;TEST @Value(rain1h) > 10;TEST @Value(rain1h) <= 20'0.403922,0.0196078,0.454902'BOOL_OP;OR;COMPOSITE_TEST;1 OR 2;TEST @Value(rain1h) > 20;TEST @Value(rain1h) <= 50'0.835294,0,0.72549'FME_NUM_CONDITIONS9___"";opacity;1;halo-fill;1,1,1;halo-radius;0;__ignore__positioning-group;FME_DISCLOSURE_OPEN;text-ratio;0;wrap-width;0;wrap-before;No;spacing;0;character-spacing;0;line-spacing;0;label-position-tolerance;0;dx;0;dy;0;avoid-edges;No;minimum-distance;0;minimum-padding;0;minimum-path-length;0;allow-overlap;No;orientation;0;placement;point;placement-type;dummy;placements;<Unused>;max-char-angle-delta;<Unused>;horizontal-alignment;auto;justify-alignment;auto;vertical-alignment;auto;__ignore__comp-group;FME_DISCLOSURE_OPEN;comp-op;src-over;FME_CONTROLLER_QUERY_FILE;;FME_CONTROLLER_CHOICE;text";Tytuł;text;"__ignore__text-properties-group;FME_DISCLOSURE_OPEN;name;tekst_deszcz;face-name;Tahoma,BOLD;size;44;__ignore__color-group;FME_DISCLOSURE_OPEN;fill;0,0,0;opacity;1;halo-fill;1,1,1;halo-radius;0;__ignore__positioning-group;FME_DISCLOSURE_OPEN;text-ratio;0;wrap-width;0;wrap-before;No;spacing;0;character-spacing;0;line-spacing;0;label-position-tolerance;0;dx;0;dy;0;avoid-edges;No;minimum-distance;0;minimum-padding;0;minimum-path-length;0;allow-overlap;No;orientation;0;placement;point;placement-type;dummy;placements;<Unused>;max-char-angle-delta;<Unused>;horizontal-alignment;auto;justify-alignment;auto;vertical-alignment;auto;__ignore__comp-group;FME_DISCLOSURE_CLOSED;comp-op;src-over;FME_CONTROLLER_QUERY_FILE;;FME_CONTROLLER_CHOICE;text";Czas;text;"__ignore__text-properties-group;FME_DISCLOSURE_OPEN;name;tekst_czas;face-name;Tahoma,Normal;size;25;__ignore__color-group;FME_DISCLOSURE_OPEN;fill;0,0,0;opacity;1;halo-fill;1,1,1;halo-radius;0;__ignore__positioning-group;FME_DISCLOSURE_CLOSED;text-ratio;0;wrap-width;0;wrap-before;No;spacing;0;character-spacing;0;line-spacing;0;label-position-tolerance;0;dx;0;dy;0;avoid-edges;No;minimum-distance;0;minimum-padding;0;minimum-path-length;0;allow-overlap;No;orientation;0;placement;point;placement-type;dummy;placements;<Unused>;max-char-angle-delta;<Unused>;horizontal-alignment;auto;justify-alignment;auto;vertical-alignment;auto;__ignore__comp-group;FME_DISCLOSURE_CLOSED;comp-op;src-over;FME_CONTROLLER_QUERY_FILE;;FME_CONTROLLER_CHOICE;text"
    NUM_COLUMNS = 1500
    NUM_ROWS = 1500
    SPECIFY_GROUND_EXTENTS = Use input data ground extents
    INTERPRETATION_TYPE_LOOKUP = RGBA32
    LAYER_CARDINALITY = Each rendering rule is a layer
    RASTER -> FeatureWriter_13 [Raster]
FeatureWriter_13
    DATASET = $(folder)
    DATASET_ATTR = _dataset
    FEATURE_TYPE_LIST_ATTR = _feature_types
    FORMAT = PNGRASTER
    PNGRASTER_COORDINATE_SYSTEM_GRANULARITY = FEATURE
    PNGRASTER_FORMAT_ATTRIBUTES_OVERRIDE_FEATURE_TYPE_PARAMETERS = No
    TOTAL_FEATURES_WRITTEN_ATTR = _total_features_written

Bookmark: Utworzenie pomocniczych danych do wykonania kompozycji (tytuły kompozycji i inne metadane)
Creator_2
    GEOMTYPE = Geometry Object
    NUM = 1
    CREATED -> VertexCreator_2
VertexCreator_2
    COORDSYS = EPSG:2180
    MEASURE_TYPE_LOOKUP = CONTINUOUS
    MODE = REPLACE
    REMOVE_ATTRIBUTES = No
    XVAL = 300000
    YVAL = 200000
    MEASURE_TYPE = Continuous
    MODE_NAME = Replace with Point
    -> DateTimeStamper_5
DateTimeStamper_5
    DATETIME_ATTR = czas
    INCLUDE_FRAC_SECONDS = YES
    INCLUDE_OFFSET = NO
    SCOPE = feature
    STAMP_TYPE = datetime
    TIMEZONE = utc
    -> DateTimeCalculator_6
DateTimeCalculator_6
    DAYS = 0
    HOURS = 1
    MINUTES = 0
    MODE = DATETIMECALC_1_ADD_INTERVAL
    MONTHS = 0
    OPERATION_PARAMETERS = START_DATETIME_DATETIMECALC_1_ADD_INTERVAL]@Value(czas)]OPERATOR]ADD]YEARS]0]MONTHS]0]DAYS]0]HOURS]1]MINUTES]0]SECONDS]0]RESULT_DATETIME]czas_nowy]START_DATETIME]@Value(czas)
    OPERATOR = ADD
    RESULT_DATETIME = czas_nowy
    SECONDS = 0
    START_DATETIME = @Value(czas)
    START_DATETIME_DATETIMECALC_1_ADD_INTERVAL = @Value(czas)
    YEARS = 0
    -> DateTimeConverter_4
DateTimeConverter_4
    DATETIME_ATTR = czas_nowy
    OUT_FORMAT = %d-%m-%Y %H:%M
    PASSTHROUGH = NO
    REPAIR_INPUT = YES
    -> AttributeManager_10
AttributeManager_10
    ATTR_TABLE:
      SET_TO tekst (varchar(47)) = Rozkład aktualnej temperatury (IMGW/eDWIN/IUNG)
      SET_TO tekst_czas (varchar(200)) = Wygenerowano: @Value(czas_nowy)
        Autor: Jakub Maciejak (BurzeInfo)
    USER_EXPOSED_ATTRIBUTES = tekst,tekst_czas
    -> MapnikRasterizer [Czas]
    -> MapnikRasterizer_2 [Czas]
    -> MapnikRasterizer_3 [Czas]
Creator
    GEOMTYPE = Geometry Object
    NUM = 1
    CREATED -> VertexCreator
VertexCreator
    COORDSYS = EPSG:2180
    MEASURE_TYPE_LOOKUP = CONTINUOUS
    MODE = REPLACE
    REMOVE_ATTRIBUTES = No
    XVAL = 500444.7460
    YVAL = 806847.5160
    MEASURE_TYPE = Continuous
    MODE_NAME = Replace with Point
    -> AttributeManager_9
AttributeManager_9
    ATTR_TABLE:
      SET_TO tekst (varchar(47)) = Rozkład aktualnej temperatury (IMGW/eDWIN/IUNG)
      SET_TO tekst_wiatr (varchar(40)) = Aktualne porywy wiatru (IMGW/eDWIN/IUNG)
      SET_TO tekst_deszcz (varchar(42)) = Opad z ostatniej godziny (IMGW/eDWIN/IUNG)
    USER_EXPOSED_ATTRIBUTES = tekst,tekst_wiatr,tekst_deszcz
    -> MapnikRasterizer_2 [Tytuł]
    -> MapnikRasterizer_3 [Tytuł]
    -> MapnikRasterizer [Tytuł]
